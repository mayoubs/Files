EGATEL-ccu9000-v18-MIB DEFINITIONS ::= BEGIN
-- **********************************************************************
-- **********************************************************************
-- **
-- **  COPYRIGHT  	(c) 2006	EGATEL, S.L.  
-- **							Avda. de Ourense, 1 - EGATEL Building
-- **							Parque Tecnologico de Galicia
-- **   						San Cibrao das Viñas, Ourense, Spain
-- **
-- ** 
-- **  MODULE    	EGATEL-ccu9000-v18-MIB.MIB
-- **  
-- **  DESCRIPTION  Egatel CCU9000.
-- **
-- **  HISTORY     2009-01-07 -> v1. initial
-- **					2009-03-30 -> v2. Increment: tONR, enableantennaLoadFailureR, enablepoutFailureR, stateantennaLoadFailureR,
-- **																			statepoutFailureR;
-- **					2009-07-24 -> v3. 		Increment: localremoteN, autorestore,autorestoreAttempt,attemptInterval,restoreTestTime;
-- **					2009-09-22 -> v4. 		Increment: autorestore_mode(by time or fault);
-- **					2010-01-22 -> v5. 		Increment: change autorestore_mode.(by time, by hour). Number max. of restore by time.;
-- **					2010-11-16 -> v6. 		Increment: G.P.S. Management;
-- **					2010-02-01 -> v10. 	Increment: Dual or single drive OIDS with GPS;
-- **					2010-11-18 -> v11. 	Increment: Dual or single drive OIDS without GPS;
-- **					2011-03-14 -> v12. 	Increment: Dual or single drive OIDS with GPS and (turbineFailVref, turbineFailMuteTime);
-- **					2011-06-29 -> v13. 	Increment: Liquid OIDS;
-- **					2011-09-14 -> v13. 	Increment: New kind of Amplifiers with liquid refrig.;
-- **					2012-07-02 -> v14. 	Increment: 16 Amps + 2 racks control
-- **					2013-11-26 -> v15. 	Increment: 8 Amps Doherty params 
-- **					2014-05-20 -> v16. 	Fault Vcc on Amps description
-- **					2015-09-02 -> v17. 	PowerControlRef OID range 0 to 499 (x 10 mVolt)
-- **					2016-09-13 -> v18.  Liquid Amps Iccs  increment.
-- **********************************************************************
-- **********************************************************************


IMPORTS

	enterprises, OBJECT-TYPE, MODULE-IDENTITY, NOTIFICATION-TYPE, Integer32
		FROM SNMPv2-SMI 
		
	DisplayString, TruthValue, TimeStamp		
		FROM SNMPv2-TC 
		
	OBJECT-GROUP, MODULE-COMPLIANCE, AGENT-CAPABILITIES, NOTIFICATION-GROUP
		FROM SNMPv2-CONF;     

----------------------------------------------------------------------------------------------
egatel17 MODULE-IDENTITY

	LAST-UPDATED "201609131000Z"
	
	ORGANIZATION "EGATEL, S.L."
	
	CONTACT-INFO
		"EGATEL, S.L.
		Avda. de Ourense, 1 - EGATEL Building
		Parque Tecnologico de Galicia
		San Cibrao, 32901, Ourense, Spain
		Tlf: (34)988368118 		Fax: (34)988368119
		Contact: http://www.egatel.es"
		
	DESCRIPTION
		"This is the root MIB module for Egatel ccu9000 N+1 and Dual/Single drive variant.
		The enterprise OID is {iso org dod internet private enterprises 19443}
		
		IANA allocated this enterprise OID for the exclusive use of EGATEL, S. L. 
		Other than internet network equipment distributed or licensed by EGATEL, S.L., 
		no other party has any right what-so-ever to distribute or license internet network 
		equipment which responds to the EGATEL enterprise OID or its subsidiary branches."	
		
				
	REVISION 	"201609131000Z"
    DESCRIPTION             
      	"version 18"
		
	::= {enterprises 19443}

----------------------------------------------------------------------
----------------------------------------------------------------------
	ccu9000 OBJECT IDENTIFIER ::= {egatel17 17} 

	mibConformance OBJECT IDENTIFIER ::= {ccu9000 100}
	
		mibGroups OBJECT IDENTIFIER ::= {mibConformance 1}
		mibCompliance OBJECT IDENTIFIER ::= {mibConformance 2}
		mibCapabilities OBJECT IDENTIFIER ::= {mibConformance 3}

	ccu9000Notif OBJECT IDENTIFIER ::= {ccu9000 101}
	
		ccu9000NotifAux OBJECT IDENTIFIER ::= {ccu9000Notif 0}
		
			notificationNode OBJECT IDENTIFIER ::= {ccu9000NotifAux 100}
				
				notificationnplusone OBJECT IDENTIFIER ::= {notificationNode 1}
				
					notificationtx1 OBJECT IDENTIFIER ::= {notificationnplusone 1}
					notificationtx2 OBJECT IDENTIFIER ::= {notificationnplusone 2}
					notificationtx3 OBJECT IDENTIFIER ::= {notificationnplusone 3}
					notificationtx4 OBJECT IDENTIFIER ::= {notificationnplusone 4}
					notificationtx5 OBJECT IDENTIFIER ::= {notificationnplusone 5}
					notificationtx6 OBJECT IDENTIFIER ::= {notificationnplusone 6}
					notificationtx7 OBJECT IDENTIFIER ::= {notificationnplusone 7}
					notificationtx8 OBJECT IDENTIFIER ::= {notificationnplusone 8}
					notificationtxR OBJECT IDENTIFIER ::= {notificationnplusone 9}
					notificationMatrix OBJECT IDENTIFIER ::= {notificationnplusone 10}
				
				notificationsddd OBJECT IDENTIFIER ::= {notificationNode 2}
				
					notificationpower OBJECT IDENTIFIER ::= {notificationsddd 1}
					notificationrack OBJECT IDENTIFIER ::= {notificationsddd 2}
					notificationexcA OBJECT IDENTIFIER ::= {notificationsddd 3}
					notificationexcB OBJECT IDENTIFIER ::= {notificationsddd 4}
				
				notificationccu OBJECT IDENTIFIER ::= {notificationNode 3}
				notificationgps OBJECT IDENTIFIER ::= {notificationNode 4}
				
		enableNotificationsnplusone OBJECT IDENTIFIER ::= {ccu9000Notif 1}
		
			enableNotificationstx1 OBJECT IDENTIFIER ::= {enableNotificationsnplusone 1}
			enableNotificationstx2 OBJECT IDENTIFIER ::= {enableNotificationsnplusone 2}
			enableNotificationstx3 OBJECT IDENTIFIER ::= {enableNotificationsnplusone 3}
			enableNotificationstx4 OBJECT IDENTIFIER ::= {enableNotificationsnplusone 4}
			enableNotificationstx5 OBJECT IDENTIFIER ::= {enableNotificationsnplusone 5}
			enableNotificationstx6 OBJECT IDENTIFIER ::= {enableNotificationsnplusone 6}
			enableNotificationstx7 OBJECT IDENTIFIER ::= {enableNotificationsnplusone 7}
			enableNotificationstx8 OBJECT IDENTIFIER ::= {enableNotificationsnplusone 8}
			enableNotificationstxR OBJECT IDENTIFIER ::= {enableNotificationsnplusone 9}
			enableNotificationsMatrix OBJECT IDENTIFIER ::= {enableNotificationsnplusone 10}
	
		enableNotificationssddd OBJECT IDENTIFIER ::= {ccu9000Notif 2}
		
			enableNotificationspower OBJECT IDENTIFIER ::= {enableNotificationssddd 1}
			enableNotificationsrack OBJECT IDENTIFIER ::= {enableNotificationssddd 2}
			enableNotificationsexcA OBJECT IDENTIFIER ::= {enableNotificationssddd 3}
			enableNotificationsexcB OBJECT IDENTIFIER ::= {enableNotificationssddd 4}
	
		enableNotificationsccu OBJECT IDENTIFIER ::= {ccu9000Notif 3}
		enableNotificationsgps OBJECT IDENTIFIER ::= {ccu9000Notif 4}
	
	stateNotifications OBJECT IDENTIFIER ::= {ccu9000 102}
	
	stateNotificationsnplusone OBJECT IDENTIFIER ::= {stateNotifications 1}
	
		stateNotificationstx1 OBJECT IDENTIFIER ::= {stateNotificationsnplusone 1}
		stateNotificationstx2 OBJECT IDENTIFIER ::= {stateNotificationsnplusone 2}
		stateNotificationstx3 OBJECT IDENTIFIER ::= {stateNotificationsnplusone 3}
		stateNotificationstx4 OBJECT IDENTIFIER ::= {stateNotificationsnplusone 4}
		stateNotificationstx5 OBJECT IDENTIFIER ::= {stateNotificationsnplusone 5}
		stateNotificationstx6 OBJECT IDENTIFIER ::= {stateNotificationsnplusone 6}
		stateNotificationstx7 OBJECT IDENTIFIER ::= {stateNotificationsnplusone 7}
		stateNotificationstx8 OBJECT IDENTIFIER ::= {stateNotificationsnplusone 8}
		stateNotificationstxR OBJECT IDENTIFIER ::= {stateNotificationsnplusone 9}
		stateNotificationsMatrix OBJECT IDENTIFIER ::= {stateNotificationsnplusone 10}
	
	stateNotificationssddd OBJECT IDENTIFIER ::= {stateNotifications 2}
	
		stateNotificationspower OBJECT IDENTIFIER ::= {stateNotificationssddd 1}
		stateNotificationsrack OBJECT IDENTIFIER ::= {stateNotificationssddd 2}
		stateNotificationsexcA OBJECT IDENTIFIER ::= {stateNotificationssddd 3}
		stateNotificationsexcB OBJECT IDENTIFIER ::= {stateNotificationssddd 4}
	
	stateNotificationsccu OBJECT IDENTIFIER ::= {stateNotifications 3}
	stateNotificationsgps OBJECT IDENTIFIER ::= {stateNotifications 4}

----------------------------------------------------------------------
----------------------------------------------------------------------
nplusone OBJECT IDENTIFIER ::= { ccu9000 1 }

tx1 OBJECT IDENTIFIER ::= { nplusone 1 }

	channel1 OBJECT-TYPE
		SYNTAX Integer32
		MAX-ACCESS read-only
		STATUS current
		DESCRIPTION
		"Transmitter 1 output channel"
	::= { tx1 1 }

	outputPower1 OBJECT-TYPE
		SYNTAX Integer32 
		MAX-ACCESS read-only
		STATUS current
		DESCRIPTION
		"Transmitter 1 Output Power (Watt)"
 	::= { tx1 2 }

	minPout1 OBJECT-TYPE
		SYNTAX Integer32
		MAX-ACCESS read-write
		STATUS current
		DESCRIPTION
		"Transmitter 1 Pout thershold (Watt)"
	::= { tx1 3 }

	onoff1 OBJECT-TYPE
		SYNTAX TruthValue 
		MAX-ACCESS read-write
		STATUS current
		DESCRIPTION
		"Transmitter 1 status:
        		ON (1),
        		OFF (2)"
	::= { tx1 4 }

	priority1 OBJECT-TYPE
		SYNTAX Integer32 (0..8)
		MAX-ACCESS read-write
		STATUS current
		DESCRIPTION
		"Transmitter 1 Conmutation priority (0 to 8); 0=> no switchable "
	::= { tx1 5 }

	tFault1 OBJECT-TYPE
		SYNTAX Integer32 (0..120)
		MAX-ACCESS read-write
		STATUS current
		DESCRIPTION
		"Transmitter 1 Fault validation time (1 to 120 seconds)"
	::= { tx1 6 }

	tON1 OBJECT-TYPE
		SYNTAX Integer32  (0..120)
		MAX-ACCESS read-write
		STATUS current
		DESCRIPTION
		"Transmitter 1 On time (1 to 120 seconds)"
	::= { tx1 7 }

	switchtx1 OBJECT-TYPE
		SYNTAX Integer32 
		MAX-ACCESS read-write
		STATUS current
		DESCRIPTION
		"Transmitter 1 switch command (SET (1)) (only in Manual mode!!)"
	::= { tx1 8 }

	excModel1 OBJECT-TYPE
		SYNTAX Integer32 
		MAX-ACCESS read-only
		STATUS current
		DESCRIPTION
		"Transmitter 1 Exciter model:
        		TDE9000 (0),
        		RED9000 (1),
        		RS232 (2),
        		CONTACTS (3)"
	::= { tx1 9 }

	faultwithWarn1 OBJECT-TYPE
		SYNTAX TruthValue 
		MAX-ACCESS read-write
		STATUS current
		DESCRIPTION
		"Transmitter 1 Warning configuration:
        		Fault with Warning (1),
        		No Fault with Warning (2)"
	::= { tx1 10 }

	faultwithAlarm1 OBJECT-TYPE
		SYNTAX TruthValue 
		MAX-ACCESS read-write
		STATUS current
      	DESCRIPTION
        	"Transmitter 1 Fault configuration:
        		Power OR Probe (1),
        		Power AND Probe (2)"
	::= { tx1 11 }

	probeLevel1 OBJECT-TYPE
    		SYNTAX Integer32 (0..100)
		MAX-ACCESS read-only
		STATUS current
		DESCRIPTION
        	"Transmitter 1 probe level (%)"
	::= { tx1 12 }

	probeThreshold1 OBJECT-TYPE
    		SYNTAX Integer32 (0..100)
	     MAX-ACCESS read-write
      	STATUS current
      	DESCRIPTION
        	"Transmitter 1 probe threshold (%)"
 	::= { tx1 13 }
 	
 	localremote1 OBJECT-TYPE
    		SYNTAX TruthValue 
	     MAX-ACCESS read-only
      	STATUS current
      	DESCRIPTION
        	"Transmitter 1 control mode:
        		LOCAL(1),
        		REMOTE (2)"
 	::= { tx1 14 }
----------------------------------------------------------------------
----------------------------------------------------------------------
    tx2 OBJECT IDENTIFIER ::= { nplusone 2 }

   	channel2 OBJECT-TYPE
    		SYNTAX Integer32
      	MAX-ACCESS read-only
      	STATUS current
      	DESCRIPTION
	        "Transmitter 2 output channel"
   	::= { tx2 1 }

    outputPower2 OBJECT-TYPE
    		SYNTAX Integer32 
	     MAX-ACCESS read-only
      	STATUS current
      	DESCRIPTION
        	"Transmitter 2 Output Power (Watt)"
 	::= { tx2 2 }

    minPout2 OBJECT-TYPE
    		SYNTAX Integer32
	    	MAX-ACCESS read-write
      	STATUS current
      	DESCRIPTION
	        "Transmitter 2 Pout thershold (Watt)"
   	::= { tx2 3 }

    onoff2 OBJECT-TYPE
    		SYNTAX TruthValue 
	     MAX-ACCESS read-write
      	STATUS current
      	DESCRIPTION
        	"Transmitter 2 status:
        		ON (1),
        		OFF (2)"
 	::= { tx2 4 }

    priority2 OBJECT-TYPE
    		SYNTAX Integer32 (0..8)
	     MAX-ACCESS read-write
      	STATUS current
      	DESCRIPTION
        	"Transmitter 2 Conmutation priority (0 to 8); 0=> no switchable "
 	::= { tx2 5 }

    tFault2 OBJECT-TYPE
    		SYNTAX Integer32 (0..120)
	     MAX-ACCESS read-write
      	STATUS current
      	DESCRIPTION
        	"Transmitter 2 Fault validation time (1 to 120 seconds)"
 	::= { tx2 6 }

    tON2 OBJECT-TYPE
    		SYNTAX Integer32 (0..120)
	     MAX-ACCESS read-write
      	STATUS current
      	DESCRIPTION
        	"Transmitter 2 On time (1 to 120 seconds)"
 	::= { tx2 7 }

    switchtx2 OBJECT-TYPE
		SYNTAX Integer32 
	     MAX-ACCESS read-write
      	STATUS current
      	DESCRIPTION
        	"Transmitter 2 switch command (SET (1)) (only in Manual mode!!)"
 	::= { tx2 8 }  

	excModel2 OBJECT-TYPE
    		SYNTAX Integer32 
	     MAX-ACCESS read-only
      	STATUS current
      	DESCRIPTION
        	"Transmitter 2 Exciter model:
        		TDE9000 (0),
        		RED9000 (1),
        		RS232 (2),
        		CONTACTS (3)"
 	::= { tx2 9 }

	faultwithWarn2 OBJECT-TYPE
    		SYNTAX TruthValue 
	     MAX-ACCESS read-write
      	STATUS current
      	DESCRIPTION
        	"Transmitter 2 Warning configuration:
        		Fault with Warning (1),
        		No Fault with Warning (2)"
 	::= { tx2 10 }

	faultwithAlarm2 OBJECT-TYPE
    		SYNTAX TruthValue 
	     MAX-ACCESS read-write
      	STATUS current
      	DESCRIPTION
        	"Transmitter 2 Fault configuration:
        		Power OR Probe (1),
        		Power AND Probe (2)"
 	::= { tx2 11 }

	probeLevel2 OBJECT-TYPE
    		SYNTAX Integer32 (0..100)
	     MAX-ACCESS read-only
      	STATUS current
      	DESCRIPTION
        	"Transmitter 2 Probe level (%)"
 	::= { tx2 12 }

	probeThreshold2 OBJECT-TYPE
    		SYNTAX Integer32 (0..100)
	     MAX-ACCESS read-write
      	STATUS current
      	DESCRIPTION
        	"Transmitter 2 Probe threshold (%)"
 	::= { tx2 13 }
 	
 	localremote2 OBJECT-TYPE
    		SYNTAX TruthValue 
	     MAX-ACCESS read-only
      	STATUS current
      	DESCRIPTION
        	"Transmitter 2 control mode:
        		LOCAL(1),
        		REMOTE (2)"
 	::= { tx2 14 }
----------------------------------------------------------------------
----------------------------------------------------------------------
    tx3 OBJECT IDENTIFIER ::= { nplusone 3 }

   	channel3 OBJECT-TYPE
    		SYNTAX Integer32
      	MAX-ACCESS read-only
      	STATUS current
      	DESCRIPTION
	        "Transmitter 3 output channel"
   	::= { tx3 1 }

    outputPower3 OBJECT-TYPE
    		SYNTAX Integer32 
	     MAX-ACCESS read-only
      	STATUS current
      	DESCRIPTION
        	"Transmitter 3 Output Power (Watt)"
 	::= { tx3 2 }

    minPout3 OBJECT-TYPE
    		SYNTAX Integer32
	    	MAX-ACCESS read-write
      	STATUS current
      	DESCRIPTION
	        "Transmitter 3 Pout thershold (Watt)"
   	::= { tx3 3 }

    onoff3 OBJECT-TYPE
    		SYNTAX TruthValue 
	     MAX-ACCESS read-write
      	STATUS current
      	DESCRIPTION
        	"Transmitter 3 status:
        		ON (1),
        		OFF (2)"
 	::= { tx3 4 }

    priority3 OBJECT-TYPE
    		SYNTAX Integer32 (0..8)
	     MAX-ACCESS read-write
      	STATUS current
      	DESCRIPTION
        	"Transmitter 3 Conmutation priority (0 to 8); 0=> no switchable "
 	::= { tx3 5 }

    tFault3 OBJECT-TYPE
    		SYNTAX Integer32 (0..120)
	     MAX-ACCESS read-write
      	STATUS current
      	DESCRIPTION
        	"Transmitter 3 Fault validation time (1 to 120 seconds)"
 	::= { tx3 6 }

    tON3 OBJECT-TYPE
    		SYNTAX Integer32 (0..120)
	     MAX-ACCESS read-write
      	STATUS current
      	DESCRIPTION
        	"Transmitter 3 On time (1 to 120 seconds)"
 	::= { tx3 7 }

    switchtx3 OBJECT-TYPE
    		SYNTAX Integer32 
	     MAX-ACCESS read-write
      	STATUS current
      	DESCRIPTION
        	"Transmitter 3 switch command (SET (1)) (only in Manual mode!!)"
 	::= { tx3 8 }

	excModel3 OBJECT-TYPE
    		SYNTAX Integer32 
	     MAX-ACCESS read-only
      	STATUS current
      	DESCRIPTION
        	"Transmitter 3 Exciter model:
        		TDE9000 (0),
        		RED9000 (1),
        		RS232 (2),
        		CONTACTS (3)"
 	::= { tx3 9 }

	faultwithWarn3 OBJECT-TYPE
    		SYNTAX TruthValue 
	     MAX-ACCESS read-write
      	STATUS current
      	DESCRIPTION
        	"Transmitter 3 Warning configuration:
        		Fault with Warning (1),
        		No Fault with Warning (2)"
 	::= { tx3 10 }

	faultwithAlarm3 OBJECT-TYPE
    		SYNTAX TruthValue 
	     MAX-ACCESS read-write
      	STATUS current
      	DESCRIPTION
        	"Transmitter 3 Fault configuration:
        		Power OR Probe (1),
        		Power AND Probe (2)"
 	::= { tx3 11 }

	probeLevel3 OBJECT-TYPE
    		SYNTAX Integer32 (0..100)
	     MAX-ACCESS read-only
      	STATUS current
      	DESCRIPTION
        	"Transmitter 3 Probe level (%)"
 	::= { tx3 12 }

	probeThreshold3 OBJECT-TYPE
    		SYNTAX Integer32 (0..100)
	     MAX-ACCESS read-write
      	STATUS current
      	DESCRIPTION
        	"Transmitter 3 Probe threshold (%)"
 	::= { tx3 13 }
 	
 	localremote3 OBJECT-TYPE
    		SYNTAX TruthValue 
	     MAX-ACCESS read-only
      	STATUS current
      	DESCRIPTION
        	"Transmitter 3 control mode:
        		LOCAL (1),
        		REMOTE (2)"
 	::= { tx3 14 }
----------------------------------------------------------------------
----------------------------------------------------------------------
    tx4 OBJECT IDENTIFIER ::= { nplusone 4 }

   	channel4 OBJECT-TYPE
    		SYNTAX Integer32
      	MAX-ACCESS read-only
      	STATUS current
      	DESCRIPTION
	        "Transmitter 4 output channel"
   	::= { tx4 1 }

    outputPower4 OBJECT-TYPE
    		SYNTAX Integer32 
	     MAX-ACCESS read-only
      	STATUS current
      	DESCRIPTION
        	"Transmitter 4 Output Power (Watt)"
 	::= { tx4 2 }

    minPout4 OBJECT-TYPE
    		SYNTAX Integer32
	    	MAX-ACCESS read-write
      	STATUS current
      	DESCRIPTION
	        "Transmitter 4 Pout thershold (Watt)"
   	::= { tx4 3 }

    onoff4 OBJECT-TYPE
    		SYNTAX TruthValue 
	     MAX-ACCESS read-write
      	STATUS current
      	DESCRIPTION
        	"Transmitter 4 status:
        		ON (1),
        		OFF (2)"
 	::= { tx4 4 }

    priority4 OBJECT-TYPE
    		SYNTAX Integer32 (0..8)
	     MAX-ACCESS read-write
      	STATUS current
      	DESCRIPTION
        	"Transmitter 4 Conmutation priority (0 to 8); 0=> no switchable "
 	::= { tx4 5 }

    tFault4 OBJECT-TYPE
    		SYNTAX Integer32 (0..120)
	     MAX-ACCESS read-write
      	STATUS current
      	DESCRIPTION
        	"Transmitter 4 Fault validation time (1 to 120 seconds)"
 	::= { tx4 6 }

    tON4 OBJECT-TYPE
    		SYNTAX Integer32 (0..120)
	     MAX-ACCESS read-write
      	STATUS current
      	DESCRIPTION
        	"Transmitter 4 On time (1 to 120 seconds)"
 	::= { tx4 7 }

    switchtx4 OBJECT-TYPE
    		SYNTAX Integer32 
	     MAX-ACCESS read-write
      	STATUS current
      	DESCRIPTION
        	"Transmitter 4 switch command (SET (1)) (only in Manual mode!!)"
 	::= { tx4 8 }

	excModel4 OBJECT-TYPE
    		SYNTAX Integer32 
	     MAX-ACCESS read-only
      	STATUS current
      	DESCRIPTION
        	"Transmitter 4 exciter model:
        		TDE9000 (0),
        		RED9000 (1),
        		RS232 (2),
        		CONTACTS (3)"
 	::= { tx4 9 }

	faultwithWarn4 OBJECT-TYPE
    		SYNTAX TruthValue 
	     MAX-ACCESS read-write
      	STATUS current
      	DESCRIPTION
        	"Transmitter 4 Warning configuration:
        		Fault with Warning (1),
        		No Fault with Warning (2)"
 	::= { tx4 10 }

	faultwithAlarm4 OBJECT-TYPE
    		SYNTAX TruthValue 
	     MAX-ACCESS read-write
      	STATUS current
      	DESCRIPTION
        	"Transmitter 4 Fault configuration: 
        		Power OR Probe (1),
        		Fault with:Power AND Probe (2)"
 	::= { tx4 11 }

	probeLevel4 OBJECT-TYPE
    		SYNTAX Integer32 (0..100)
	     MAX-ACCESS read-only
      	STATUS current
      	DESCRIPTION
        	"Transmitter 4 Probe level (%)"
 	::= { tx4 12 }

	probeThreshold4 OBJECT-TYPE
    		SYNTAX Integer32 (0..100)
	     MAX-ACCESS read-write
      	STATUS current
      	DESCRIPTION
        	"Transmitter 4 probe threshold (%)"
 	::= { tx4 13 }
 	
 	localremote4 OBJECT-TYPE
    		SYNTAX TruthValue 
	     MAX-ACCESS read-only
      	STATUS current
      	DESCRIPTION
        	"Transmitter 4 control mode:
        		LOCAL (1),
        		REMOTE (2)"
 	::= { tx4 14 }
 ----------------------------------------------------------------------
----------------------------------------------------------------------
    tx5 OBJECT IDENTIFIER ::= { nplusone 5 }

   	channel5 OBJECT-TYPE
    		SYNTAX Integer32
      	MAX-ACCESS read-only
      	STATUS current
      	DESCRIPTION
	        "Transmitter 5 output channel"
   	::= { tx5 1 }

    outputPower5 OBJECT-TYPE
    		SYNTAX Integer32 
	     MAX-ACCESS read-only
      	STATUS current
      	DESCRIPTION
        	"Transmitter 5 Output Power (Watt)"
 	::= { tx5 2 }

    minPout5 OBJECT-TYPE
    		SYNTAX Integer32
	    	MAX-ACCESS read-write
      	STATUS current
      	DESCRIPTION
	        "Transmitter 5 Pout thershold (Watt)"
   	::= { tx5 3 }

    onoff5 OBJECT-TYPE
    		SYNTAX TruthValue 
	     MAX-ACCESS read-write
      	STATUS current
      	DESCRIPTION
        	"Transmitter 5 status:
        		ON (1),
        		OFF (2)"
 	::= { tx5 4 }

    priority5 OBJECT-TYPE
    		SYNTAX Integer32 (0..8)
	     MAX-ACCESS read-write
      	STATUS current
      	DESCRIPTION
        	"Transmitter 5 Conmutation priority (0 to 8); 0=> no switchable "
 	::= { tx5 5 }

    tFault5 OBJECT-TYPE
    		SYNTAX Integer32 (0..120)
	     MAX-ACCESS read-write
      	STATUS current
      	DESCRIPTION
        	"Transmitter 5 Fault validation time (1 to 120 seconds)"
 	::= { tx5 6 }

    tON5 OBJECT-TYPE
    		SYNTAX Integer32 (0..120)
	     MAX-ACCESS read-write
      	STATUS current
      	DESCRIPTION
        	"Transmitter 5 On time (1 to 120 seconds)"
 	::= { tx5 7 }

    switchtx5 OBJECT-TYPE
    		SYNTAX Integer32 
	     MAX-ACCESS read-write
      	STATUS current
      	DESCRIPTION
        	"Transmitter 5 switch command (SET (1)) (only in Manual mode!!)"
 	::= { tx5 8 }

	excModel5 OBJECT-TYPE
    		SYNTAX Integer32 
	     MAX-ACCESS read-only
      	STATUS current
      	DESCRIPTION
        	"Transmitter 5 Exciter model:
        		TDE9000 (0),
        		RED9000 (1),
        		RS232 (2),
        		CONTACTS (3)"
 	::= { tx5 9 }

	faultwithWarn5 OBJECT-TYPE
    		SYNTAX TruthValue 
	     MAX-ACCESS read-write
      	STATUS current
      	DESCRIPTION
        	"Transmitter 5 Warning configuration:
        		Fault with Warning (1),
        		No Fault with Warning (2)"
 	::= { tx5 10 }

	faultwithAlarm5 OBJECT-TYPE
    		SYNTAX TruthValue 
	     MAX-ACCESS read-write
      	STATUS current
      	DESCRIPTION
        	"Transmitter 5 Fault configuration:
        		Power OR Probe (1),
        		Power AND Probe (2)"
 	::= { tx5 11 }

	probeLevel5 OBJECT-TYPE
    		SYNTAX Integer32 (0..100)
	     MAX-ACCESS read-only
      	STATUS current
      	DESCRIPTION
        	"Transmitter 5 Probe level (%)"
 	::= { tx5 12 }

	probeThreshold5 OBJECT-TYPE
    		SYNTAX Integer32 (0..100)
	     MAX-ACCESS read-write
      	STATUS current
      	DESCRIPTION
        	"Transmitter 5 Probe threshold (%)"
 	::= { tx5 13 }
 	
 	localremote5 OBJECT-TYPE
    		SYNTAX TruthValue 
	     MAX-ACCESS read-only
      	STATUS current
      	DESCRIPTION
        	"Transmitter 5 cntrol mode:
        		LOCAL (1)
        		REMOTE (2)"
 	::= { tx5 14 }
  ----------------------------------------------------------------------
----------------------------------------------------------------------
tx6 OBJECT IDENTIFIER ::= { nplusone 6 }

   	channel6 OBJECT-TYPE
    		SYNTAX Integer32
      	MAX-ACCESS read-only
      	STATUS current
      	DESCRIPTION
	        "Transmitter 6 output channel"
   	::= { tx6 1 }

    outputPower6 OBJECT-TYPE
    		SYNTAX Integer32 
	     MAX-ACCESS read-only
      	STATUS current
      	DESCRIPTION
        	"Transmitter 6 Output Power (Watt)"
 	::= { tx6 2 }

    minPout6 OBJECT-TYPE
    		SYNTAX Integer32
	    	MAX-ACCESS read-write
      	STATUS current
      	DESCRIPTION
	        "Transmitter 6 Pout thershold (Watt)"
   	::= { tx6 3 }

    onoff6 OBJECT-TYPE
    		SYNTAX TruthValue 
	     MAX-ACCESS read-write
      	STATUS current
      	DESCRIPTION
        	"Transmitter 6 status:
        		ON (1),
        		OFF (2)"
 	::= { tx6 4 }

    priority6 OBJECT-TYPE
    		SYNTAX Integer32 (0..8)
	     MAX-ACCESS read-write
      	STATUS current
      	DESCRIPTION
        	"Transmitter 6 Conmutation priority (0 to 8); 0=> no switchable "
 	::= { tx6 5 }

    tFault6 OBJECT-TYPE
    		SYNTAX Integer32 (0..120)
	     MAX-ACCESS read-write
      	STATUS current
      	DESCRIPTION
        	"Transmitter 6 Fault validation time (1 to 120 seconds)"
 	::= { tx6 6 }

    tON6 OBJECT-TYPE
    		SYNTAX Integer32 (0..120)
	     MAX-ACCESS read-write
      	STATUS current
      	DESCRIPTION
        	"Transmitter 6 On time (1 to 120 seconds)"
 	::= { tx6 7 }

    switchtx6 OBJECT-TYPE
    		SYNTAX Integer32 
	     MAX-ACCESS read-write
      	STATUS current
      	DESCRIPTION
        	"Transmitter 6 switch command (SET (1)) (only in Manual mode!!)"
 	::= { tx6 8 }

	excModel6 OBJECT-TYPE
    		SYNTAX Integer32 
	     MAX-ACCESS read-only
      	STATUS current
      	DESCRIPTION
        	"Transmitter 6 Exciter model:
        		TDE9000 (0),
        		RED9000 (1),
        		RS232 (2),
        		CONTACTS (3)"
 	::= { tx6 9 }

	faultwithWarn6 OBJECT-TYPE
    		SYNTAX TruthValue 
	     MAX-ACCESS read-write
      	STATUS current
      	DESCRIPTION
        	"Transmitter 6 Warning configuration:
        		Fault with Warning (1),
        		No Fault with Warning (2)"
 	::= { tx6 10 }

	faultwithAlarm6 OBJECT-TYPE
    		SYNTAX TruthValue 
	     MAX-ACCESS read-write
      	STATUS current
      	DESCRIPTION
        	"Transmitter 6 Fault configuration:
        		Power OR Probe (1),
        		Power AND Probe (2)"
 	::= { tx6 11 }

	probeLevel6 OBJECT-TYPE
    		SYNTAX Integer32 (0..100)
	     MAX-ACCESS read-only
      	STATUS current
      	DESCRIPTION
        	"Transmitter 6 Probe level (%)"
 	::= { tx6 12 }

	probeThreshold6 OBJECT-TYPE
    		SYNTAX Integer32 (0..100)
	     MAX-ACCESS read-write
      	STATUS current
      	DESCRIPTION
        	"Transmitter 6 Probe threshold (%)"
 	::= { tx6 13 }
 	
 	localremote6 OBJECT-TYPE
    		SYNTAX TruthValue 
	     MAX-ACCESS read-only
      	STATUS current
      	DESCRIPTION
        	"Transmitter 6 control mode:
        		LOCAL (1),
        		REMOTE (2)"
 	::= { tx6 14 }
  ----------------------------------------------------------------------
----------------------------------------------------------------------
    tx7 OBJECT IDENTIFIER ::= { nplusone 7 }

   	channel7 OBJECT-TYPE
    		SYNTAX Integer32
      	MAX-ACCESS read-only
      	STATUS current
      	DESCRIPTION
	        "Transmitter 7 output channel"
   	::= { tx7 1 }

    outputPower7 OBJECT-TYPE
    		SYNTAX Integer32 
	     MAX-ACCESS read-only
      	STATUS current
      	DESCRIPTION
        	"Transmitter 7 Output Power (Watt)"
 	::= { tx7 2 }

    minPout7 OBJECT-TYPE
    		SYNTAX Integer32
	    	MAX-ACCESS read-write
      	STATUS current
      	DESCRIPTION
	        "Transmitter 7 Pout thershold (Watt)"
   	::= { tx7 3 }

    onoff7 OBJECT-TYPE
    		SYNTAX TruthValue 
	     MAX-ACCESS read-write
      	STATUS current
      	DESCRIPTION
        	"Transmitter 7 status:
        		ON (1),
        		OFF (2)"
 	::= { tx7 4 }

    priority7 OBJECT-TYPE
    		SYNTAX Integer32 (0..8)
	     MAX-ACCESS read-write
      	STATUS current
      	DESCRIPTION
        	"Transmitter 7 Conmutation priority (0 to 8); 0=> no switchable "
 	::= { tx7 5 }

    tFault7 OBJECT-TYPE
    		SYNTAX Integer32 (0..120)
	     MAX-ACCESS read-write
      	STATUS current
      	DESCRIPTION
        	"Transmitter 7 Fault validation time (1 to 120 seconds)"
 	::= { tx7 6 }

    tON7 OBJECT-TYPE
    		SYNTAX Integer32 (0..120)
	     MAX-ACCESS read-write
      	STATUS current
      	DESCRIPTION
        	"Transmitter 7 On time (1 to 120 seconds)"
 	::= { tx7 7 }

    switchtx7 OBJECT-TYPE
    		SYNTAX Integer32 
	     MAX-ACCESS read-write
      	STATUS current
      	DESCRIPTION
        	"Transmitter 7 switch command (SET (1)) (only in Manual mode!!)"
 	::= { tx7 8 }

	excModel7 OBJECT-TYPE
    		SYNTAX Integer32 
	     MAX-ACCESS read-only
      	STATUS current
      	DESCRIPTION
        	"Transmitter 7 Exciter model:
        		TDE9000 (0),
        		RED9000 (1),
        		RS232 (2),
        		CONTACTS (3)"
 	::= { tx7 9 }

	faultwithWarn7 OBJECT-TYPE
    		SYNTAX TruthValue 
	     MAX-ACCESS read-write
      	STATUS current
      	DESCRIPTION
        	"Transmitter 7 Warning configuration:
        		Fault with Warning (1),
        		No Fault with Warning (2)"
 	::= { tx7 10 }

	faultwithAlarm7 OBJECT-TYPE
    		SYNTAX TruthValue 
	     MAX-ACCESS read-write
      	STATUS current
      	DESCRIPTION
        	"Transmitter 7 Fault configuration:
        		Power OR Probe (1),
        		Power AND Probe (2)"
 	::= { tx7 11 }

	probeLevel7 OBJECT-TYPE
    		SYNTAX Integer32 (0..100)
	     MAX-ACCESS read-only
      	STATUS current
      	DESCRIPTION
        	"Transmitter 7 Probe level (%)"
 	::= { tx7 12 }

	probeThreshold7 OBJECT-TYPE
    		SYNTAX Integer32 (0..100)
	     MAX-ACCESS read-write
      	STATUS current
      	DESCRIPTION
        	"Transmitter 7 Probe threshold (%)"
 	::= { tx7 13 }
 	
 	localremote7 OBJECT-TYPE
    		SYNTAX TruthValue 
	     MAX-ACCESS read-only
      	STATUS current
      	DESCRIPTION
        	"Transmitter 7 control mode:
        		LOCAL (1),
        		REMOTE (2)"
 	::= { tx7 14 }
 ----------------------------------------------------------------------
----------------------------------------------------------------------
    tx8 OBJECT IDENTIFIER ::= { nplusone 8 }

   	channel8 OBJECT-TYPE
    		SYNTAX Integer32
      	MAX-ACCESS read-only
      	STATUS current
      	DESCRIPTION
	        "Transmitter 8 output channel"
   	::= { tx8 1 }

    outputPower8 OBJECT-TYPE
    		SYNTAX Integer32 
	     MAX-ACCESS read-only
      	STATUS current
      	DESCRIPTION
        	"Transmitter 8 Output Power (Watt)"
 	::= { tx8 2 }

    minPout8 OBJECT-TYPE
    		SYNTAX Integer32
	    	MAX-ACCESS read-write
      	STATUS current
      	DESCRIPTION
	        "Transmitter 8 Pout thershold (Watt)"
   	::= { tx8 3 }

    onoff8 OBJECT-TYPE
    		SYNTAX TruthValue 
	     MAX-ACCESS read-write
      	STATUS current
      	DESCRIPTION
        	"Transmitter 8 status:
        		ON (1),
        		OFF (2)"
 	::= { tx8 4 }

    priority8 OBJECT-TYPE
    		SYNTAX Integer32 (0..8)
	     MAX-ACCESS read-write
      	STATUS current
      	DESCRIPTION
        	"Transmitter 8 Conmutation priority (0 to 8); 0=> no switchable "
 	::= { tx8 5 }

    tFault8 OBJECT-TYPE
    		SYNTAX Integer32 (0..120)
	     MAX-ACCESS read-write
      	STATUS current
      	DESCRIPTION
        	"Transmitter 8 Fault validation time (1 to 120 seconds)"
 	::= { tx8 6 }

    tON8 OBJECT-TYPE
    		SYNTAX Integer32 (0..120)
	     MAX-ACCESS read-write
      	STATUS current
      	DESCRIPTION
        	"Transmitter 8 On time (1 to 120 seconds)"
 	::= { tx8 7 }

    switchtx8 OBJECT-TYPE
    		SYNTAX Integer32 
	     MAX-ACCESS read-write
      	STATUS current
      	DESCRIPTION
        	"Transmitter 8 switch command (SET (1)) (only in Manual mode!!)"
 	::= { tx8 8 }

	excModel8 OBJECT-TYPE
    		SYNTAX Integer32 
	     MAX-ACCESS read-only
      	STATUS current
      	DESCRIPTION
        	"Transmitter 8 Exciter model:
        		TDE9000 (0),
        		RED9000 (1),
        		RS232 (2),
        		CONTACTS (3)"
 	::= { tx8 9 }

	faultwithWarn8 OBJECT-TYPE
    		SYNTAX TruthValue 
	     MAX-ACCESS read-write
      	STATUS current
      	DESCRIPTION
        	"Transmitter 8 Warning configuration:
        		Fault with Warning (1),
        		No Fault with Warning (2)"
 	::= { tx8 10 }

	faultwithAlarm8 OBJECT-TYPE
    		SYNTAX TruthValue 
	     MAX-ACCESS read-write
      	STATUS current
      	DESCRIPTION
        	"Transmitter 8 Fault configuration:
        		Power OR Probe (1),
        		Fault with:Power AND Probe (2)"
 	::= { tx8 11 }

	probeLevel8 OBJECT-TYPE
    		SYNTAX Integer32 (0..100)
	     MAX-ACCESS read-only
      	STATUS current
      	DESCRIPTION
        	"Transmitter 8 Probe level (%)"
 	::= { tx8 12 }

	probeThreshold8 OBJECT-TYPE
    		SYNTAX Integer32 (0..100)
	     MAX-ACCESS read-write
      	STATUS current
      	DESCRIPTION
        	"Transmitter 8 Probe threshold (%)"
 	::= { tx8 13 }
 	
 	localremote8 OBJECT-TYPE
    		SYNTAX TruthValue 
	     MAX-ACCESS read-only
      	STATUS current
      	DESCRIPTION
        	"Transmitter 8 control mode:
        		LOCAL (1),
        		REMOTE (2)"
 	::= { tx8 14 }
  ----------------------------------------------------------------------
----------------------------------------------------------------------
    txR OBJECT IDENTIFIER ::= { nplusone 9 }

   	channelR OBJECT-TYPE
    		SYNTAX Integer32
      	MAX-ACCESS read-only
      	STATUS current
      	DESCRIPTION
	        "Reserve Transmitter output channel"
   	::= { txR 1 }

    outputPowerR OBJECT-TYPE
    		SYNTAX Integer32 
	     MAX-ACCESS read-only
      	STATUS current
      	DESCRIPTION
        	"Reserve Transmitter Output Power (Watt)"
 	::= { txR 2 }

    onoffR OBJECT-TYPE
    		SYNTAX TruthValue 
	     MAX-ACCESS read-write
      	STATUS current
      	DESCRIPTION
        	"Reserve Transmitter status:
        		ON (1),
        		OFF (2)"
 	::= { txR 3 }

    tONR OBJECT-TYPE
    		SYNTAX Integer32 (0..120)
	     MAX-ACCESS read-write
      	STATUS current
      	DESCRIPTION
        	"Reserve Transmitter On time (1 to 120 seconds)"
 	::= { txR 4 }

    switchRESET OBJECT-TYPE
    		SYNTAX Integer32 
	     MAX-ACCESS read-write
      	STATUS current
      	DESCRIPTION
        	"All main Transmitters to Antenna and Reserve Transmitter  to Load (SET (1))"
 	::= { txR 5 }

	excModelR OBJECT-TYPE
    		SYNTAX Integer32 
	     MAX-ACCESS read-only
      	STATUS current
      	DESCRIPTION
        	"Reserve Transmitter Exciter model:
        		TDE9000 (0),
        		RED9000 (1)"
 	::= { txR 6 }

	probeLevelR OBJECT-TYPE
    		SYNTAX Integer32 (0..100)
	     MAX-ACCESS read-only
      	STATUS current
      	DESCRIPTION
        	"Reserve Transmitter Probe level (%)"
 	::= { txR 7 }

	probeThresholdR OBJECT-TYPE
    		SYNTAX Integer32 (0..100)
	     MAX-ACCESS read-write
      	STATUS current
      	DESCRIPTION
        	"Reserve Transmitter Probe threshold (%)"
 	::= { txR 8 }
 	
 	localremoteR OBJECT-TYPE
    		SYNTAX TruthValue 
	     MAX-ACCESS read-only
      	STATUS current
      	DESCRIPTION
        	"Reserve Transmitter control mode:
        		LOCAL (1),
        		REMOTE (2)"
 	::= { txR 9 }
--------------------------------------------------------
--------------------------------------------------------
confignplusone OBJECT IDENTIFIER ::= { nplusone 10 }

    ntx OBJECT-TYPE
    		SYNTAX Integer32 (0..8)
      	MAX-ACCESS read-only
      	STATUS current
      	DESCRIPTION
	        "Number of controlled main transmitters (0 to 8)"
   	::= { confignplusone 1 }
   	
   	autorestore OBJECT-TYPE
    		SYNTAX TruthValue 
      	MAX-ACCESS read-write
      	STATUS current
      	DESCRIPTION
	        "Auto Restore:
	        	OFF (1),
	        	ON (2)"
   	::= { confignplusone 2 }
   	
   	testAttempts OBJECT-TYPE
    		SYNTAX Integer32 (1..50)
      	MAX-ACCESS read-write
      	STATUS current
      	DESCRIPTION
	        "Test Attempts. Max: 50"
   	::= { confignplusone 3 }
   	
   	attemptInterval OBJECT-TYPE
    		SYNTAX Integer32 (1..1440)
      	MAX-ACCESS read-write
      	STATUS current
      	DESCRIPTION
	        "Test Attempts Time Interval.
           Max: 1.440 min. (24 hours)"
   	::= { confignplusone 4 }
   	
   	testTime OBJECT-TYPE
    		SYNTAX Integer32 (1..1440)
      	MAX-ACCESS read-write
      	STATUS current
      	DESCRIPTION
	        "Test Time max: 1440 min. (24 hours)"
   	::= { confignplusone 5 }
   	
   	testMode OBJECT-TYPE
    		SYNTAX TruthValue 
      	MAX-ACCESS read-write
      	STATUS current
      	DESCRIPTION
	        "Test Mode:
	        	By TIME (1),
	        	By HOUR (2)"
   	::= { confignplusone 6 }

   	testHour OBJECT-TYPE
    		SYNTAX DisplayString (SIZE (5))
      	MAX-ACCESS read-write
      	STATUS current
      	DESCRIPTION
	        "Hour of the day for Test. Format: XX:XX"
   	::= { confignplusone 7 }
   	
		restorationMaxNumber OBJECT-TYPE
    		SYNTAX Integer32 
      	MAX-ACCESS read-write
      	STATUS current
      	DESCRIPTION
	        "Max number of restorations. Max: 10"
   	::= { confignplusone 8 }
   	
   	attemptIntervalRestorations OBJECT-TYPE
    		SYNTAX Integer32 (1..30)
      	MAX-ACCESS read-write
      	STATUS current
      	DESCRIPTION
	        "Time Interval for Max number of restorations (days)"
   	::= { confignplusone 9 }

   	txLoadTest OBJECT-TYPE
    		SYNTAX Integer32 
      	MAX-ACCESS read-only
      	STATUS current
      	DESCRIPTION
	        "Transmitter to load test:
           	Not aplicable (0),
           	Fault (1),
           	OK (2)"
   	::= { confignplusone 10 }

   	testPhase OBJECT-TYPE
    		SYNTAX Integer32 (0..3)
      	MAX-ACCESS read-only
      	STATUS current
      	DESCRIPTION
	        "Test phase for trasmitter to load:
			Not aplicable (0),
			Waiting for test (1),
			Testing (2),
			Test completed (3)"
   	::= { confignplusone 11 }

   	testAttemptsExecuted OBJECT-TYPE
    		SYNTAX Integer32 
      	MAX-ACCESS read-only
      	STATUS current
      	DESCRIPTION
	        "Test Attempts Executed."
   	::= { confignplusone 12 }

   	numberRestorationsTX1 OBJECT-TYPE
    		SYNTAX Integer32 
      	MAX-ACCESS read-only
      	STATUS current
      	DESCRIPTION
	        "Number of restorations for transmitter 1."
   	::= { confignplusone 13 }

   	numberRestorationsTX2 OBJECT-TYPE
    		SYNTAX Integer32 
      	MAX-ACCESS read-only
      	STATUS current
      	DESCRIPTION
	        "Number of restorations for  transmitter 2."
   	::= { confignplusone 14 }

   	numberRestorationsTX3 OBJECT-TYPE
    		SYNTAX Integer32 
      	MAX-ACCESS read-only
      	STATUS current
      	DESCRIPTION
	        "Number of restorations for  transmitter 3."
   	::= { confignplusone 15 }

   	numberRestorationsTX4 OBJECT-TYPE
    		SYNTAX Integer32 
      	MAX-ACCESS read-only
      	STATUS current
      	DESCRIPTION
	        "Number of restorations for  transmitter 4."
   	::= { confignplusone 16 }

   	numberRestorationsTX5 OBJECT-TYPE
    		SYNTAX Integer32 
      	MAX-ACCESS read-only
      	STATUS current
      	DESCRIPTION
	        "Number of restorations for  transmitter 5."
   	::= { confignplusone 17 }

   	numberRestorationsTX6 OBJECT-TYPE
    		SYNTAX Integer32 
      	MAX-ACCESS read-only
      	STATUS current
      	DESCRIPTION
	        "Number of restorations for  transmitter 6."
   	::= { confignplusone 18 }

   	numberRestorationsTX7 OBJECT-TYPE
    		SYNTAX Integer32 
      	MAX-ACCESS read-only
      	STATUS current
      	DESCRIPTION
	        "Number of restorations for  transmitter 7."
   	::= { confignplusone 19 }

   	numberRestorationsTX8 OBJECT-TYPE
    		SYNTAX Integer32 
      	MAX-ACCESS read-only
      	STATUS current
      	DESCRIPTION
	        "Number of restorations for  transmitter 8."
   	::= { confignplusone 20 }
   	
----------------------------------------------------------
----------------------------------------------------------
 asiMatrix OBJECT IDENTIFIER ::= { nplusone 11 }

	matrixActive OBJECT-TYPE
    		SYNTAX TruthValue 
      	MAX-ACCESS read-only
      	STATUS current
      	DESCRIPTION
	        "ASI Matrix active: 
	        	YES (1),
	        	NO (2)"
   	::= { asiMatrix 1 }

	autoMan OBJECT-TYPE
    		SYNTAX TruthValue 
      	MAX-ACCESS read-write
      	STATUS current
      	DESCRIPTION
	        "Switch Mode:
	        	Automatic (1),
	        	Manual (2)"
   	::= { asiMatrix 2 }

	asiSelect OBJECT-TYPE
    		SYNTAX Integer32 (1..8)
      	MAX-ACCESS read-write
      	STATUS current
      	DESCRIPTION
	        "ASI selected to reserve"
   	::= { asiMatrix 3 }

----------------------------------------------------------
----------------------------------------------------------
singleDualDrive OBJECT IDENTIFIER ::= { ccu9000 2 }

power OBJECT IDENTIFIER ::= { singleDualDrive 1 }
		
	outputPower OBJECT-TYPE
    		SYNTAX Integer32 
      	MAX-ACCESS read-only
      	STATUS current
      	DESCRIPTION
	        "Forward power (Watts)"
   	::= { power 1 }
   		
   	reflectedPower OBJECT-TYPE
    		SYNTAX Integer32 
      	MAX-ACCESS read-only
      	STATUS current
      	DESCRIPTION
	        "Reflected power (Watts)"
	::= { power 2 }
   		
   	nominalPower OBJECT-TYPE
    		SYNTAX Integer32 
      	MAX-ACCESS read-only
      	STATUS current
      	DESCRIPTION
	        "Nominal power (Watts)"
   	::= { power 3 }
   		
   	minPowerThreshold OBJECT-TYPE
    		SYNTAX Integer32 (0..9999)
      	MAX-ACCESS read-write
      	STATUS current
      	DESCRIPTION
	        "Minimun power threshold (Watts)
	         Range: 0 - 9999W"
   	::= { power 4 }
   		
   	maxReflectedThreshold OBJECT-TYPE
    		SYNTAX Integer32 (0..999)
      	MAX-ACCESS read-write
      	STATUS current
      	DESCRIPTION
	        "Maximun reflected power threshold (Watts)
	         Range: 0 - 999W"
   	::= { power 5 }
   		
   	powerControlRef OBJECT-TYPE
    		SYNTAX Integer32 (0..499)
      	MAX-ACCESS read-write
      	STATUS current
      	DESCRIPTION
	        "Power control reference voltaje:
				0 to 499 (x10 mVolts)"
   	::= { power 6 }
   		
   	commAmplifiers OBJECT-TYPE
		SYNTAX TruthValue
		MAX-ACCESS read-write
		STATUS current
		DESCRIPTION
			"Communications with amplifiers
				YES (1),
				NO (2)"
	::= { power 7 }
   		
	nAmplifiers OBJECT-TYPE
		SYNTAX Integer32
		MAX-ACCESS read-only
		STATUS current
		DESCRIPTION
			"Number of amplifiers"
	::= { power 8 }
----------------------------------------------------------
  amplifier1 OBJECT IDENTIFIER ::= { power 9 }

	pdAmplifier1 OBJECT-TYPE
		SYNTAX Integer32
		MAX-ACCESS read-only
		STATUS current
		DESCRIPTION
			"Output power (Watts) amplifier 1"
	::= {amplifier1 1 }

	prAmplifier1 OBJECT-TYPE
		SYNTAX Integer32
		MAX-ACCESS read-only
		STATUS current
		DESCRIPTION
			"Reflected power (/10 Volts) amplifier 1"
	::= {amplifier1 2 }

	pinAmplifier1 OBJECT-TYPE
		SYNTAX Integer32
		MAX-ACCESS read-only
		STATUS current
		DESCRIPTION
			"Input power (/10 Volts) amplifier 1"
	::= {amplifier1 3 }

	temperatureAmplifier1 OBJECT-TYPE
		SYNTAX Integer32
		MAX-ACCESS read-only
		STATUS current
		DESCRIPTION
			"Temperature (C) amplifier 1"
	::= {amplifier1 4 }

	vcagAmplifier1 OBJECT-TYPE
		SYNTAX Integer32
		MAX-ACCESS read-only
		STATUS current
		DESCRIPTION
			"CAG voltage (/10 Volts) amplifier 1"
	::= {amplifier1 5 }

	vfaseAmplifier1 OBJECT-TYPE
		SYNTAX Integer32
		MAX-ACCESS read-only
		STATUS current
		DESCRIPTION
			"Fase voltage (/10 Volts) amplifier 1"
	::= {amplifier1 6 }

	ipdrAmplifier1 OBJECT-TYPE
		SYNTAX Integer32
		MAX-ACCESS read-only
		STATUS current
		DESCRIPTION
			"Predriver current (/10 A) amplifier 1"
	::= {amplifier1 7 }

	idrAmplifier1 OBJECT-TYPE
		SYNTAX Integer32
		MAX-ACCESS read-only
		STATUS current
		DESCRIPTION
			"Driver current (/10 A) amplifier 1"
	::= {amplifier1 8 }

	it1Amplifier1 OBJECT-TYPE
		SYNTAX Integer32
		MAX-ACCESS read-only
		STATUS current
		DESCRIPTION
			"Transistor 1 current (/10 A) in amplifier 1"
	::= {amplifier1 9 }

	it2Amplifier1 OBJECT-TYPE
		SYNTAX Integer32
		MAX-ACCESS read-only
		STATUS current
		DESCRIPTION
			"Transistor 2 current (/10 A) in amplifier 1"
	::= {amplifier1 10 }

	it3Amplifier1 OBJECT-TYPE
		SYNTAX Integer32
		MAX-ACCESS read-only
		STATUS current
		DESCRIPTION
			"Transistor 3 current (/10 A) in amplifier 1"
	::= {amplifier1 11 }

	it4Amplifier1 OBJECT-TYPE
		SYNTAX Integer32
		MAX-ACCESS read-only
		STATUS current
		DESCRIPTION
			"Transistor 4 current (/10 A) in amplifier 1"
	::= {amplifier1 12 }

	it5Amplifier1 OBJECT-TYPE
		SYNTAX Integer32
		MAX-ACCESS read-only
		STATUS current
		DESCRIPTION
			"Transistor 5 current (/10 A) in amplifier 1"
	::= {amplifier1 13 }

	it6Amplifier1 OBJECT-TYPE
		SYNTAX Integer32
		MAX-ACCESS read-only
		STATUS current
		DESCRIPTION
			"Transistor 6 current (/10 A) in amplifier 1"
	::= {amplifier1 14 }

	it7Amplifier1 OBJECT-TYPE
		SYNTAX Integer32
		MAX-ACCESS read-only
		STATUS current
		DESCRIPTION
			"Transistor 7 current (/10 A) in amplifier 1"
	::= {amplifier1 15 }

	it8Amplifier1 OBJECT-TYPE
		SYNTAX Integer32
		MAX-ACCESS read-only
		STATUS current
		DESCRIPTION
			"Transistor 8 current (/10 A) in amplifier 1"
	::= {amplifier1 16 }
	
	it9IFAN1amplifier1 OBJECT-TYPE
		SYNTAX Integer32
		MAX-ACCESS read-only
		STATUS current
		DESCRIPTION
			"Transistor 9/ FAN 1 current (/10 A) in amplifier 1"
	::= {amplifier1 17 }

	it10IFAN2amplifier1 OBJECT-TYPE
		SYNTAX Integer32
		MAX-ACCESS read-only
		STATUS current
		DESCRIPTION
			"Transistor 10/ FAN 2 current (/10 A) in amplifier 1"
	::= {amplifier1 18 }

	faultPinAmplifier1 OBJECT-TYPE
		SYNTAX Integer32
		MAX-ACCESS read-only
		STATUS current
		DESCRIPTION
			"Fault Input Power Amplifier 1
				FAULT (1),
				OK (2)"
	::= {amplifier1 19 }

	faultVccAmplifier1 OBJECT-TYPE
		SYNTAX Integer32
		MAX-ACCESS read-only
		STATUS current
		DESCRIPTION
			"Faulty Power supply"
	::= {amplifier1 20 }

	futureUseAmplifier1 OBJECT-TYPE
		SYNTAX Integer32
		MAX-ACCESS read-only
		STATUS current
		DESCRIPTION
		"Air: Doherty Optimal Channel Amplifier 1"
			
	::= {amplifier1 21 }
	
	it11amplifier1 OBJECT-TYPE
		SYNTAX Integer32
		MAX-ACCESS read-only
		STATUS current
		DESCRIPTION
		"Air: Doherty Low Frequency 
		 Liquid: Transistor 11 current (/10 A) in amplifier 1"
		
	::= {amplifier1 22 }
	
	it12amplifier1 OBJECT-TYPE
		SYNTAX Integer32
		MAX-ACCESS read-only
		STATUS current
		DESCRIPTION
		"Air: Doherty Hight Frequency 
		 Liquid: Transistor 12 current (/10 A) in amplifier 1"
	::= {amplifier1 23 }
	
	muteAmplifier1 OBJECT-TYPE
		SYNTAX Integer32
		MAX-ACCESS read-only
		STATUS current
		DESCRIPTION
			"Doherty muted by frequency error 
			    Muted (1),
				OK (2)"
	::= {amplifier1 24 }
--------------------------------------------------------
	amplifier2 OBJECT IDENTIFIER ::= { power 10 }

	pdAmplifier2 OBJECT-TYPE
		SYNTAX Integer32
		MAX-ACCESS read-only
		STATUS current
		DESCRIPTION
			"Output power (Watts) amplifier 2"
	::= {amplifier2 1 }

	prAmplifier2 OBJECT-TYPE
		SYNTAX Integer32
		MAX-ACCESS read-only
		STATUS current
		DESCRIPTION
			"Reflected power (/10 Volts) amplifier 2"
	::= {amplifier2 2 }

	pinAmplifier2 OBJECT-TYPE
		SYNTAX Integer32
		MAX-ACCESS read-only
		STATUS current
		DESCRIPTION
			"Input power (/10 Volts) amplifier 2"
	::= {amplifier2 3 }

	temperatureAmplifier2 OBJECT-TYPE
		SYNTAX Integer32
		MAX-ACCESS read-only
		STATUS current
		DESCRIPTION
			"Temperature (C) amplifier 2"
	::= {amplifier2 4 }

	vcagAmplifier2 OBJECT-TYPE
		SYNTAX Integer32
		MAX-ACCESS read-only
		STATUS current
		DESCRIPTION
			"CAG voltage (/10 Volts) amplifier 2"
	::= {amplifier2 5 }

	vfaseAmplifier2 OBJECT-TYPE
		SYNTAX Integer32
		MAX-ACCESS read-only
		STATUS current
		DESCRIPTION
			"Fase voltage (/10 Volts) amplifier 2"
	::= {amplifier2 6 }
	
	ipdrAmplifier2 OBJECT-TYPE
		SYNTAX Integer32
		MAX-ACCESS read-only
		STATUS current
		DESCRIPTION
			"Predriver current (/10 A) amplifier 2"
	::= {amplifier2 7 }

	idrAmplifier2 OBJECT-TYPE
		SYNTAX Integer32
		MAX-ACCESS read-only
		STATUS current
		DESCRIPTION
			"Driver current (/10 A) amplifier 2"
	::= {amplifier2 8 }

	it1Amplifier2 OBJECT-TYPE
		SYNTAX Integer32
		MAX-ACCESS read-only
		STATUS current
		DESCRIPTION
			"Transistor 1 current (/10 A) in amplifier 2"
	::= {amplifier2 9 }

	it2Amplifier2 OBJECT-TYPE
		SYNTAX Integer32
		MAX-ACCESS read-only
		STATUS current
		DESCRIPTION
			"Transistor 2 current (/10 A) in amplifier 2"
	::= {amplifier2 10 }

	it3Amplifier2 OBJECT-TYPE
		SYNTAX Integer32
		MAX-ACCESS read-only
		STATUS current
		DESCRIPTION
			"Transistor 3 current (/10 A) in amplifier 2"
	::= {amplifier2 11 }

	it4Amplifier2 OBJECT-TYPE
		SYNTAX Integer32
		MAX-ACCESS read-only
		STATUS current
		DESCRIPTION
			"Transistor 4 current (/10 A) in amplifier 2"
	::= {amplifier2 12 }

	it5Amplifier2 OBJECT-TYPE
		SYNTAX Integer32
		MAX-ACCESS read-only
		STATUS current
		DESCRIPTION
			"Transistor 5 current (/10 A) in amplifier 2"
	::= {amplifier2 13 }

	it6Amplifier2 OBJECT-TYPE
		SYNTAX Integer32
		MAX-ACCESS read-only
		STATUS current
		DESCRIPTION
			"Transistor 6 current (/10 A) in amplifier 2"
	::= {amplifier2 14 }

	it7Amplifier2 OBJECT-TYPE
		SYNTAX Integer32
		MAX-ACCESS read-only
		STATUS current
		DESCRIPTION
			"Transistor 7 current (/10 A) in amplifier 2"
	::= {amplifier2 15 }

	it8Amplifier2 OBJECT-TYPE
		SYNTAX Integer32
		MAX-ACCESS read-only
		STATUS current
		DESCRIPTION
			"Transistor 8 current (/10 A) in amplifier 2"
	::= {amplifier2 16 }

	it9IFAN1amplifier2 OBJECT-TYPE
		SYNTAX Integer32
		MAX-ACCESS read-only
		STATUS current
		DESCRIPTION
			"Transistor 9/ FAN 1 current (/10 A) in amplifier 2"
	::= {amplifier2 17 }

	it10IFAN2amplifier2 OBJECT-TYPE
		SYNTAX Integer32
		MAX-ACCESS read-only
		STATUS current
		DESCRIPTION
			"Transistor 10/ FAN 2 current (/10 A) in amplifier 2"
	::= {amplifier2 18 }

	faultPinAmplifier2 OBJECT-TYPE
		SYNTAX Integer32
		MAX-ACCESS read-only
		STATUS current
		DESCRIPTION
			"Fault Input Power Amplifier 2
				FAULT (1),
				OK (2)"
	::= {amplifier2 19 }

	faultVccAmplifier2 OBJECT-TYPE
		SYNTAX Integer32
		MAX-ACCESS read-only
		STATUS current
		DESCRIPTION
			"Faulty Power supply"
	::= {amplifier2 20 }

	futureUseAmplifier2 OBJECT-TYPE
		SYNTAX Integer32
		MAX-ACCESS read-only
		STATUS current
		DESCRIPTION
			"Doherty Optimal Channel Amplifier 2"
	::= {amplifier2 21 }
	
	it11amplifier2 OBJECT-TYPE
		SYNTAX Integer32
		MAX-ACCESS read-only
		STATUS current
		DESCRIPTION
			"Air: Doherty Low Frequency 
		 Liquid: Transistor 11 current (/10 A) in amplifier 2"
	::= {amplifier2 22 }
	
	it12amplifier2 OBJECT-TYPE
		SYNTAX Integer32
		MAX-ACCESS read-only
		STATUS current
		DESCRIPTION
			"Air: Doherty Hight Frequency 
		 Liquid: Transistor 12 current (/10 A) in amplifier 2"
	::= {amplifier2 23 }
	
	muteAmplifier2 OBJECT-TYPE
		SYNTAX Integer32
		MAX-ACCESS read-only
		STATUS current
		DESCRIPTION
			"Doherty muted by frequency error 
			    Muted (1),
				OK (2)"
	::= {amplifier2 24 }
--------------------------------------------------------
	amplifier3 OBJECT IDENTIFIER ::= { power 11 }

	pdAmplifier3 OBJECT-TYPE
		SYNTAX Integer32
		MAX-ACCESS read-only
		STATUS current
		DESCRIPTION
			"Output power (Watts) amplifier 3"
	::= {amplifier3 1 }

	prAmplifier3 OBJECT-TYPE
		SYNTAX Integer32
		MAX-ACCESS read-only
		STATUS current
		DESCRIPTION
			"Reflected power (/10 Volts) amplifier 3"
	::= {amplifier3 2 }

	pinAmplifier3 OBJECT-TYPE
		SYNTAX Integer32
		MAX-ACCESS read-only
		STATUS current
		DESCRIPTION
			"Input power (/10 Volts) amplifier 3"
	::= {amplifier3 3 }

	temperatureAmplifier3 OBJECT-TYPE
		SYNTAX Integer32
		MAX-ACCESS read-only
		STATUS current
		DESCRIPTION
			"Temperature (C) amplifier 3"
	::= {amplifier3 4 }

	vcagAmplifier3 OBJECT-TYPE
		SYNTAX Integer32
		MAX-ACCESS read-only
		STATUS current
		DESCRIPTION
			"CAG voltage (/10 Volts) amplifier 3"
	::= {amplifier3 5 }

	vfaseAmplifier3 OBJECT-TYPE
		SYNTAX Integer32
		MAX-ACCESS read-only
		STATUS current
		DESCRIPTION
			"Fase voltage (/10 Volts) amplifier 3"
	::= {amplifier3 6 }

	ipdrAmplifier3 OBJECT-TYPE
		SYNTAX Integer32
		MAX-ACCESS read-only
		STATUS current
		DESCRIPTION
			"Predriver current (/10 A) amplifier 3"
	::= {amplifier3 7 }

	idrAmplifier3 OBJECT-TYPE
		SYNTAX Integer32
		MAX-ACCESS read-only
		STATUS current
		DESCRIPTION
			"Driver current (/10 A) amplifier 3"
	::= {amplifier3 8 }

	it1Amplifier3 OBJECT-TYPE
		SYNTAX Integer32
		MAX-ACCESS read-only
		STATUS current
		DESCRIPTION
			"Transistor 1 current (/10 A) in amplifier 3"
	::= {amplifier3 9 }

	it2Amplifier3 OBJECT-TYPE
		SYNTAX Integer32
		MAX-ACCESS read-only
		STATUS current
		DESCRIPTION
			"Transistor 2 current (/10 A) in amplifier 3"
	::= {amplifier3 10 }

	it3Amplifier3 OBJECT-TYPE
		SYNTAX Integer32
		MAX-ACCESS read-only
		STATUS current
		DESCRIPTION
			"Transistor 3 current (/10 A) in amplifier 3"
	::= {amplifier3 11 }

	it4Amplifier3 OBJECT-TYPE
		SYNTAX Integer32
		MAX-ACCESS read-only
		STATUS current
		DESCRIPTION
			"Transistor 4 current (/10 A) in amplifier 3"
	::= {amplifier3 12 }

	it5Amplifier3 OBJECT-TYPE
		SYNTAX Integer32
		MAX-ACCESS read-only
		STATUS current
		DESCRIPTION
			"Transistor 5 current (/10 A) in amplifier 3"
	::= {amplifier3 13 }

	it6Amplifier3 OBJECT-TYPE
		SYNTAX Integer32
		MAX-ACCESS read-only
		STATUS current
		DESCRIPTION
			"Transistor 6 current (/10 A) in amplifier 3"
	::= {amplifier3 14 }

	it7Amplifier3 OBJECT-TYPE
		SYNTAX Integer32
		MAX-ACCESS read-only
		STATUS current
		DESCRIPTION
			"Transistor 7 current (/10 A) in amplifier 3"
	::= {amplifier3 15 }

	it8Amplifier3 OBJECT-TYPE
		SYNTAX Integer32
		MAX-ACCESS read-only
		STATUS current
		DESCRIPTION
			"Transistor 8 current(/10 A) in amplifier 3"
	::= {amplifier3 16 }

	it9IFAN1amplifier3 OBJECT-TYPE
		SYNTAX Integer32
		MAX-ACCESS read-only
		STATUS current
		DESCRIPTION
			"Transistor 9/ FAN 1 current (/10 A) in amplifier 3"
	::= {amplifier3 17 }

	it10IFAN2amplifier3 OBJECT-TYPE
		SYNTAX Integer32
		MAX-ACCESS read-only
		STATUS current
		DESCRIPTION
			"Transistor 10/ FAN 2 current (/10 A) in amplifier 3"
	::= {amplifier3 18 }

	faultPinAmplifier3 OBJECT-TYPE
		SYNTAX Integer32
		MAX-ACCESS read-only
		STATUS current
		DESCRIPTION
			"Fault Input Power Amplifier 3
				FAULT (1)
				OK (2)"
	::= {amplifier3 19 }

	faultVccAmplifier3 OBJECT-TYPE
		SYNTAX Integer32
		MAX-ACCESS read-only
		STATUS current
		DESCRIPTION
			"Faulty Power supply"
	::= {amplifier3 20 }

	futureUseAmplifier3 OBJECT-TYPE
		SYNTAX Integer32
		MAX-ACCESS read-only
		STATUS current
		DESCRIPTION
			"Doherty Optimal Channel Amplifier 3"
	::= {amplifier3 21 }
	
	it11amplifier3 OBJECT-TYPE
		SYNTAX Integer32
		MAX-ACCESS read-only
		STATUS current
		DESCRIPTION
			"Air: Doherty Low Frequency 
		 Liquid: Transistor 11 current (/10 A) in amplifier 3"
	::= {amplifier3 22 }
	
	it12amplifier3 OBJECT-TYPE
		SYNTAX Integer32
		MAX-ACCESS read-only
		STATUS current
		DESCRIPTION
			"Air: Doherty Hight Frequency 
		 Liquid: Transistor 12 current (/10 A) in amplifier 3"
	::= {amplifier3 23 }
	
	muteAmplifier3 OBJECT-TYPE
		SYNTAX Integer32
		MAX-ACCESS read-only
		STATUS current
		DESCRIPTION
			"Doherty muted by frequency error 
			    Muted (1),
				OK (2)"
	::= {amplifier3 24 }
--------------------------------------------------------
	amplifier4 OBJECT IDENTIFIER ::= { power 12 }

	pdAmplifier4 OBJECT-TYPE
		SYNTAX Integer32
		MAX-ACCESS read-only
		STATUS current
		DESCRIPTION
			"Output power (Watts) Amplifier 4"
	::= {amplifier4 1 }

	prAmplifier4 OBJECT-TYPE
		SYNTAX Integer32
		MAX-ACCESS read-only
		STATUS current
		DESCRIPTION
			"Reflected power (/10 Volts) Amplifier 4"
	::= {amplifier4 2 }

	pinAmplifier4 OBJECT-TYPE
		SYNTAX Integer32
		MAX-ACCESS read-only
		STATUS current
		DESCRIPTION
			"Input power (/10 Volts) Amplifier 4"
	::= {amplifier4 3 }

	temperatureAmplifier4 OBJECT-TYPE
		SYNTAX Integer32
		MAX-ACCESS read-only
		STATUS current
		DESCRIPTION
			"Temperature (C) Amplifier 4"
	::= {amplifier4 4 }

	vcagAmplifier4 OBJECT-TYPE
		SYNTAX Integer32
		MAX-ACCESS read-only
		STATUS current
		DESCRIPTION
			"CAG voltage (/10 Volts) Amplifier 4"
	::= {amplifier4 5 }

	vfaseAmplifier4 OBJECT-TYPE
		SYNTAX Integer32
		MAX-ACCESS read-only
		STATUS current
		DESCRIPTION
			"Fase voltage(/10 Volts) Amplifier 4"
	::= {amplifier4 6 }

	ipdrAmplifier4 OBJECT-TYPE
		SYNTAX Integer32
		MAX-ACCESS read-only
		STATUS current
		DESCRIPTION
			"Predriver current (/10 A) Amplifier 4"
	::= {amplifier4 7 }

	idrAmplifier4 OBJECT-TYPE
		SYNTAX Integer32
		MAX-ACCESS read-only
		STATUS current
		DESCRIPTION
			"Driver current (/10 A) Amplifier 4"
	::= {amplifier4 8 }

	it1Amplifier4 OBJECT-TYPE
		SYNTAX Integer32
		MAX-ACCESS read-only
		STATUS current
		DESCRIPTION
			"Transistor 1 current (/10 A) in Amplifier 4"
	::= {amplifier4 9 }

	it2Amplifier4 OBJECT-TYPE
		SYNTAX Integer32
		MAX-ACCESS read-only
		STATUS current
		DESCRIPTION
			"Transistor 2 current (/10 A) in Amplifier 4"
	::= {amplifier4 10 }

	it3Amplifier4 OBJECT-TYPE
		SYNTAX Integer32
		MAX-ACCESS read-only
		STATUS current
		DESCRIPTION
			"Transistor 3 current (/10 A) in Amplifier 4"
	::= {amplifier4 11 }

	it4Amplifier4 OBJECT-TYPE
		SYNTAX Integer32
		MAX-ACCESS read-only
		STATUS current
		DESCRIPTION
			"Transistor 4 current (/10 A) in Amplifier 4"
	::= {amplifier4 12 }

	it5Amplifier4 OBJECT-TYPE
		SYNTAX Integer32
		MAX-ACCESS read-only
		STATUS current
		DESCRIPTION
			"Transistor 5 current (/10 A) in Amplifier 4"
	::= {amplifier4 13 }

	it6Amplifier4 OBJECT-TYPE
		SYNTAX Integer32
		MAX-ACCESS read-only
		STATUS current
		DESCRIPTION
			"Transistor 6 current (/10 A) in Amplifier 4"
	::= {amplifier4 14 }

	it7Amplifier4 OBJECT-TYPE
		SYNTAX Integer32
		MAX-ACCESS read-only
		STATUS current
		DESCRIPTION
			"Transistor 7 current (/10 A) in Amplifier 4"
	::= {amplifier4 15 }

	it8Amplifier4 OBJECT-TYPE
		SYNTAX Integer32
		MAX-ACCESS read-only
		STATUS current
		DESCRIPTION
			"Transistor 8 current (/10 A) in Amplifier 4"
	::= {amplifier4 16 }

	it9IFAN1amplifier4 OBJECT-TYPE
		SYNTAX Integer32
		MAX-ACCESS read-only
		STATUS current
		DESCRIPTION
			"Transistor 9/ FAN 1 current (/10 A) in amplifier 4"
	::= {amplifier4 17 }

	it10IFAN2amplifier4 OBJECT-TYPE
		SYNTAX Integer32
		MAX-ACCESS read-only
		STATUS current
		DESCRIPTION
			"Transistor 10/ FAN 2 current (/10 A) in amplifier 4"
	::= {amplifier4 18 }

	faultPinAmplifier4 OBJECT-TYPE
		SYNTAX Integer32
		MAX-ACCESS read-only
		STATUS current
		DESCRIPTION
			"Fault Input Power Amplifier 4
				FAULT (1)
				OK (2)"
	::= {amplifier4 19 }

	faultVccAmplifier4 OBJECT-TYPE
		SYNTAX Integer32
		MAX-ACCESS read-only
		STATUS current
		DESCRIPTION
			"Faulty Power supply"
	::= {amplifier4 20 }	
	
	futureUseAmplifier4 OBJECT-TYPE
		SYNTAX Integer32
		MAX-ACCESS read-only
		STATUS current
		DESCRIPTION
			"Doherty Optimal Channel Amplifier 4"
	::= {amplifier4 21 }
	
	it11amplifier4 OBJECT-TYPE
		SYNTAX Integer32
		MAX-ACCESS read-only
		STATUS current
		DESCRIPTION
			"Air: Doherty Low Frequency 
		 Liquid: Transistor 11 current (/10 A) in amplifier 4"
	::= {amplifier4 22 }
	
	it12amplifier4 OBJECT-TYPE
		SYNTAX Integer32
		MAX-ACCESS read-only
		STATUS current
		DESCRIPTION
			"Air: Doherty Low Frequency 
		 Liquid: Transistor 12 current (/10 A) in amplifier 4"
	::= {amplifier4 23 }
	
	muteAmplifier4 OBJECT-TYPE
		SYNTAX Integer32
		MAX-ACCESS read-only
		STATUS current
		DESCRIPTION
			"Doherty muted by frequency error 
			    Muted (1),
				OK (2)"
	::= {amplifier4 24 }
--------------------------------------------------------
	amplifier5 OBJECT IDENTIFIER ::= { power 13 }

	pdAmplifier5 OBJECT-TYPE
		SYNTAX Integer32
		MAX-ACCESS read-only
		STATUS current
		DESCRIPTION
			"Output power (Watts) Amplifier 5"
	::= {amplifier5 1 }

	prAmplifier5 OBJECT-TYPE
		SYNTAX Integer32
		MAX-ACCESS read-only
		STATUS current
		DESCRIPTION
			"Reflected power (/10 Volts) Amplifier 5"
	::= {amplifier5 2 }

	pinAmplifier5 OBJECT-TYPE
		SYNTAX Integer32
		MAX-ACCESS read-only
		STATUS current
		DESCRIPTION
			"Input power (/10 Volts) Amplifier 5"
	::= {amplifier5 3 }

	temperatureAmplifier5 OBJECT-TYPE
		SYNTAX Integer32
		MAX-ACCESS read-only
		STATUS current
		DESCRIPTION
			"Temperature (C) Amplifier 5"
	::= {amplifier5 4 }

	vcagAmplifier5 OBJECT-TYPE
		SYNTAX Integer32
		MAX-ACCESS read-only
		STATUS current
		DESCRIPTION
			"CAG voltage (/10 Volts) Amplifier 5"
	::= {amplifier5 5 }

	vfaseAmplifier5 OBJECT-TYPE
		SYNTAX Integer32
		MAX-ACCESS read-only
		STATUS current
		DESCRIPTION
			"Fase voltage (/10 Volts) Amplifier 5"
	::= {amplifier5 6 }

	ipdrAmplifier5 OBJECT-TYPE
		SYNTAX Integer32
		MAX-ACCESS read-only
		STATUS current
		DESCRIPTION
			"Predriver current (/10 A) Amplifier 5"
	::= {amplifier5 7 }

	idrAmplifier5 OBJECT-TYPE
		SYNTAX Integer32
		MAX-ACCESS read-only
		STATUS current
		DESCRIPTION
			"Driver current (/10 A) Amplifier 5"
	::= {amplifier5 8 }

	it1Amplifier5 OBJECT-TYPE
		SYNTAX Integer32
		MAX-ACCESS read-only
		STATUS current
		DESCRIPTION
			"Transistor 1 current (/10 A) in Amplifier 5"
	::= {amplifier5 9 }

	it2Amplifier5 OBJECT-TYPE
		SYNTAX Integer32
		MAX-ACCESS read-only
		STATUS current
		DESCRIPTION
			"Transistor 2 current (/10 A) in Amplifier 5"
	::= {amplifier5 10 }

	it3Amplifier5 OBJECT-TYPE
		SYNTAX Integer32
		MAX-ACCESS read-only
		STATUS current
		DESCRIPTION
			"Transistor 3 current (/10 A) in Amplifier 5"
	::= {amplifier5 11 }

	it4Amplifier5 OBJECT-TYPE
		SYNTAX Integer32
		MAX-ACCESS read-only
		STATUS current
		DESCRIPTION
			"Transistor 4 current (/10 A) in Amplifier 5"
	::= {amplifier5 12 }

	it5Amplifier5 OBJECT-TYPE
		SYNTAX Integer32
		MAX-ACCESS read-only
		STATUS current
		DESCRIPTION
			"Transistor 5 current (/10 A) in Amplifier 5"
	::= {amplifier5 13 }

	it6Amplifier5 OBJECT-TYPE
		SYNTAX Integer32
		MAX-ACCESS read-only
		STATUS current
		DESCRIPTION
			"Transistor 6 current (/10 A) in Amplifier 5"
	::= {amplifier5 14 }

	it7Amplifier5 OBJECT-TYPE
		SYNTAX Integer32
		MAX-ACCESS read-only
		STATUS current
		DESCRIPTION
			"Transistor 7 current (/10 A) in Amplifier 5"
	::= {amplifier5 15 }

	it8Amplifier5 OBJECT-TYPE
		SYNTAX Integer32
		MAX-ACCESS read-only
		STATUS current
		DESCRIPTION
			"Transistor 8 current (/10 A) in Amplifier 5"
	::= {amplifier5 16 }

	it9IFAN1amplifier5 OBJECT-TYPE
		SYNTAX Integer32
		MAX-ACCESS read-only
		STATUS current
		DESCRIPTION
			"Transistor 9/ FAN 1 current (/10 A) in amplifier 5"
	::= {amplifier5 17 }

	it10IFAN2amplifier5 OBJECT-TYPE
		SYNTAX Integer32
		MAX-ACCESS read-only
		STATUS current
		DESCRIPTION
			"Transistor 10/ FAN 2 current (/10 A) in amplifier 5"
	::= {amplifier5 18 }

	faultPinAmplifier5 OBJECT-TYPE
		SYNTAX Integer32
		MAX-ACCESS read-only
		STATUS current
		DESCRIPTION
			"Fault Input Power Amplifier 5
				FAULT (1)
				OK (2)"
	::= {amplifier5 19 }

	faultVccAmplifier5 OBJECT-TYPE
		SYNTAX Integer32
		MAX-ACCESS read-only
		STATUS current
		DESCRIPTION
			"Faulty Power supply"
	::= {amplifier5 20 }

	futureUseAmplifier5 OBJECT-TYPE
		SYNTAX Integer32
		MAX-ACCESS read-only
		STATUS current
		DESCRIPTION
			"Doherty Optimal Channel Amplifier 5"
	::= {amplifier5 21 }
	
	it11amplifier5 OBJECT-TYPE
		SYNTAX Integer32
		MAX-ACCESS read-only
		STATUS current
		DESCRIPTION
			"Air: Doherty Low Frequency 
		 Liquid: Transistor 11 current (/10 A) in amplifier 5"
	::= {amplifier5 22 }
	
	it12amplifier5 OBJECT-TYPE
		SYNTAX Integer32
		MAX-ACCESS read-only
		STATUS current
		DESCRIPTION
			"Air: Doherty Low Frequency 
		 Liquid: Transistor 12 current (/10 A) in amplifier 5"
	::= {amplifier5 23 }
	
	muteAmplifier5 OBJECT-TYPE
		SYNTAX Integer32
		MAX-ACCESS read-only
		STATUS current
		DESCRIPTION
			"Doherty muted by frequency error 
			    Muted (1),
				OK (2)"
	::= {amplifier5 24 }
--------------------------------------------------------
	amplifier6 OBJECT IDENTIFIER ::= { power 14 }

	pdAmplifier6 OBJECT-TYPE
		SYNTAX Integer32
		MAX-ACCESS read-only
		STATUS current
		DESCRIPTION
			"Output power (Watts) Amplifier 6"
	::= {amplifier6 1 }

	prAmplifier6 OBJECT-TYPE
		SYNTAX Integer32
		MAX-ACCESS read-only
		STATUS current
		DESCRIPTION
			"Reflected power (/10 Volts) Amplifier 6"
	::= {amplifier6 2 }

	pinAmplifier6 OBJECT-TYPE
		SYNTAX Integer32
		MAX-ACCESS read-only
		STATUS current
		DESCRIPTION
			"Input power (/10 Volts) Amplifier 6"
	::= {amplifier6 3 }

	temperatureAmplifier6 OBJECT-TYPE
		SYNTAX Integer32
		MAX-ACCESS read-only
		STATUS current
		DESCRIPTION
			"Temperature (C) Amplifier 6"
	::= {amplifier6 4 }

	vcagAmplifier6 OBJECT-TYPE
		SYNTAX Integer32
		MAX-ACCESS read-only
		STATUS current
		DESCRIPTION
			"CAG voltage (/10 Volts) Amplifier 6"
	::= {amplifier6 5 }

	vfaseAmplifier6 OBJECT-TYPE
		SYNTAX Integer32
		MAX-ACCESS read-only
		STATUS current
		DESCRIPTION
			"Fase voltage(/10 Volts) Amplifier 6"
	::= {amplifier6 6 }

	ipdrAmplifier6 OBJECT-TYPE
		SYNTAX Integer32
		MAX-ACCESS read-only
		STATUS current
		DESCRIPTION
			"Predriver current (/10 A) Amplifier 6"
	::= {amplifier6 7 }

	idrAmplifier6 OBJECT-TYPE
		SYNTAX Integer32
		MAX-ACCESS read-only
		STATUS current
		DESCRIPTION
			"Driver current (/10 A) Amplifier 6"
	::= {amplifier6 8 }

	it1Amplifier6 OBJECT-TYPE
		SYNTAX Integer32
		MAX-ACCESS read-only
		STATUS current
		DESCRIPTION
			"Transistor 1 current (/10 A) in Amplifier 6"
	::= {amplifier6 9 }

	it2Amplifier6 OBJECT-TYPE
		SYNTAX Integer32
		MAX-ACCESS read-only
		STATUS current
		DESCRIPTION
			"Transistor 2 current (/10 A) in Amplifier 6"
	::= {amplifier6 10 }

	it3Amplifier6 OBJECT-TYPE
		SYNTAX Integer32
		MAX-ACCESS read-only
		STATUS current
		DESCRIPTION
			"Transistor 3 current (/10 A) in Amplifier 6"
	::= {amplifier6 11 }

	it4Amplifier6 OBJECT-TYPE
		SYNTAX Integer32
		MAX-ACCESS read-only
		STATUS current
		DESCRIPTION
			"Transistor 4 current (/10 A) in Amplifier 6"
	::= {amplifier6 12 }

	it5Amplifier6 OBJECT-TYPE
		SYNTAX Integer32
		MAX-ACCESS read-only
		STATUS current
		DESCRIPTION
			"Transistor 5 current (/10 A) in Amplifier 6"
	::= {amplifier6 13 }

	it6Amplifier6 OBJECT-TYPE
		SYNTAX Integer32
		MAX-ACCESS read-only
		STATUS current
		DESCRIPTION
			"Transistor 6 current (/10 A) in Amplifier 6"
	::= {amplifier6 14 }

	it7Amplifier6 OBJECT-TYPE
		SYNTAX Integer32
		MAX-ACCESS read-only
		STATUS current
		DESCRIPTION
			"Transistor 7 current (/10 A) in Amplifier 6"
	::= {amplifier6 15 }

	it8Amplifier6 OBJECT-TYPE
		SYNTAX Integer32
		MAX-ACCESS read-only
		STATUS current
		DESCRIPTION
			"Transistor 8 current (/10 A) in Amplifier 6"
	::= {amplifier6 16 }

	it9IFAN1amplifier6 OBJECT-TYPE
		SYNTAX Integer32
		MAX-ACCESS read-only
		STATUS current
		DESCRIPTION
			"Transistor 9/ FAN 1 current (/10 A) in amplifier 6"
	::= {amplifier6 17 }

	it10IFAN2amplifier6 OBJECT-TYPE
		SYNTAX Integer32
		MAX-ACCESS read-only
		STATUS current
		DESCRIPTION
			"Transistor 10/ FAN 2 current (/10 A) in amplifier 6"
	::= {amplifier6 18 }

	faultPinAmplifier6 OBJECT-TYPE
		SYNTAX Integer32
		MAX-ACCESS read-only
		STATUS current
		DESCRIPTION
			"Fault Input Power Amplifier 6
				FAULT (1)
				OK (2)"
	::= {amplifier6 19 }

	faultVccAmplifier6 OBJECT-TYPE
		SYNTAX Integer32
		MAX-ACCESS read-only
		STATUS current
		DESCRIPTION
			"Faulty Power supply"
	::= {amplifier6 20 }

	futureUseAmplifier6 OBJECT-TYPE
		SYNTAX Integer32
		MAX-ACCESS read-only
		STATUS current
		DESCRIPTION
			"Doherty Optimal Channel Amplifier 6"
	::= {amplifier6 21 }
	
	it11amplifier6 OBJECT-TYPE
		SYNTAX Integer32
		MAX-ACCESS read-only
		STATUS current
		DESCRIPTION
			"Air: Doherty Low Frequency 
		 Liquid: Transistor 11 current (/10 A) in amplifier 6"
	::= {amplifier6 22 }
	
	it12amplifier6 OBJECT-TYPE
		SYNTAX Integer32
		MAX-ACCESS read-only
		STATUS current
		DESCRIPTION
			"Air: Doherty Low Frequency 
		 Liquid: Transistor 12 current (/10 A) in amplifier 6"
	::= {amplifier6 23 }
	
	muteAmplifier6 OBJECT-TYPE
		SYNTAX Integer32
		MAX-ACCESS read-only
		STATUS current
		DESCRIPTION
			"Doherty muted by frequency error 
			    Muted (1),
				OK (2)"
	::= {amplifier6 24 }
--------------------------------------------------------
	amplifier7 OBJECT IDENTIFIER ::= { power 15 }

	pdAmplifier7 OBJECT-TYPE
		SYNTAX Integer32
		MAX-ACCESS read-only
		STATUS current
		DESCRIPTION
			"Output power (Watts) Amplifier 7"
	::= {amplifier7 1 }

	prAmplifier7 OBJECT-TYPE
		SYNTAX Integer32
		MAX-ACCESS read-only
		STATUS current
		DESCRIPTION
			"Reflected power (/10 Volts) Amplifier 7"
	::= {amplifier7 2 }

	pinAmplifier7 OBJECT-TYPE
		SYNTAX Integer32
		MAX-ACCESS read-only
		STATUS current
		DESCRIPTION
			"Input power (/10 Volts) Amplifier 7"
	::= {amplifier7 3 }

	temperatureAmplifier7 OBJECT-TYPE
		SYNTAX Integer32
		MAX-ACCESS read-only
		STATUS current
		DESCRIPTION
			"Temperature (C) Amplifier 7"
	::= {amplifier7 4 }

	vcagAmplifier7 OBJECT-TYPE
		SYNTAX Integer32
		MAX-ACCESS read-only
		STATUS current
		DESCRIPTION
			"CAG voltage (/10 Volts) Amplifier 7"
	::= {amplifier7 5 }

	vfaseAmplifier7 OBJECT-TYPE
		SYNTAX Integer32
		MAX-ACCESS read-only
		STATUS current
		DESCRIPTION
			"Fase voltage (/10 Volts) Amplifier 7"
	::= {amplifier7 6 }

	ipdrAmplifier7 OBJECT-TYPE
		SYNTAX Integer32
		MAX-ACCESS read-only
		STATUS current
		DESCRIPTION
			"Predriver current (/10 A) Amplifier 7"
	::= {amplifier7 7 }

	idrAmplifier7 OBJECT-TYPE
		SYNTAX Integer32
		MAX-ACCESS read-only
		STATUS current
		DESCRIPTION
			"Driver current (/10 A) Amplifier 7"
	::= {amplifier7 8 }

	it1Amplifier7 OBJECT-TYPE
		SYNTAX Integer32
		MAX-ACCESS read-only
		STATUS current
		DESCRIPTION
			"Transistor 1 current (/10 A) in Amplifier 7"
	::= {amplifier7 9 }

	it2Amplifier7 OBJECT-TYPE
		SYNTAX Integer32
		MAX-ACCESS read-only
		STATUS current
		DESCRIPTION
			"Transistor 2 current (/10 A) in Amplifier 7"
	::= {amplifier7 10 }

	it3Amplifier7 OBJECT-TYPE
		SYNTAX Integer32
		MAX-ACCESS read-only
		STATUS current
		DESCRIPTION
			"Transistor 3 current (/10 A) in Amplifier 7"
	::= {amplifier7 11 }

	it4Amplifier7 OBJECT-TYPE
		SYNTAX Integer32
		MAX-ACCESS read-only
		STATUS current
		DESCRIPTION
			"Transistor 4 current (/10 A) in Amplifier 7"
	::= {amplifier7 12 }

	it5Amplifier7 OBJECT-TYPE
		SYNTAX Integer32
		MAX-ACCESS read-only
		STATUS current
		DESCRIPTION
			"Transistor 5 current (/10 A) in Amplifier 7"
	::= {amplifier7 13 }

	it6Amplifier7 OBJECT-TYPE
		SYNTAX Integer32
		MAX-ACCESS read-only
		STATUS current
		DESCRIPTION
			"Transistor 6 current (/10 A) in Amplifier 7"
	::= {amplifier7 14 }

	it7Amplifier7 OBJECT-TYPE
		SYNTAX Integer32
		MAX-ACCESS read-only
		STATUS current
		DESCRIPTION
			"Transistor 7 current (/10 A) in Amplifier 7"
	::= {amplifier7 15 }

	it8Amplifier7 OBJECT-TYPE
		SYNTAX Integer32
		MAX-ACCESS read-only
		STATUS current
		DESCRIPTION
			"Transistor 8 current (/10 A) in Amplifier 7"
	::= {amplifier7 16 }

	it9IFAN1amplifier7 OBJECT-TYPE
		SYNTAX Integer32
		MAX-ACCESS read-only
		STATUS current
		DESCRIPTION
			"Transistor 9/ FAN 1 current (/10 A) in amplifier 7"
	::= {amplifier7 17 }

	it10IFAN2amplifier7 OBJECT-TYPE
		SYNTAX Integer32
		MAX-ACCESS read-only
		STATUS current
		DESCRIPTION
			"Transistor 10/ FAN 2 current (/10 A) in amplifier 7"
	::= {amplifier7 18 }

	faultPinAmplifier7 OBJECT-TYPE
		SYNTAX Integer32
		MAX-ACCESS read-only
		STATUS current
		DESCRIPTION
			"Fault Input Power Amplifier 7
				FAULT (1)
				OK (2)"
	::= {amplifier7 19 }

	faultVccAmplifier7 OBJECT-TYPE
		SYNTAX Integer32
		MAX-ACCESS read-only
		STATUS current
		DESCRIPTION
			"Faulty Power supply"
	::= {amplifier7 20 }
	
	futureUseAmplifier7 OBJECT-TYPE
		SYNTAX Integer32
		MAX-ACCESS read-only
		STATUS current
		DESCRIPTION
			"Doherty Optimal Channel Amplifier 7"
	::= {amplifier7 21 }
	
	it11amplifier7 OBJECT-TYPE
		SYNTAX Integer32
		MAX-ACCESS read-only
		STATUS current
		DESCRIPTION
			"Air: Doherty Low Frequency 
		 Liquid: Transistor 11 current (/10 A) in amplifier 7"
	::= {amplifier7 22 }
	
	it12amplifier7 OBJECT-TYPE
		SYNTAX Integer32
		MAX-ACCESS read-only
		STATUS current
		DESCRIPTION
			"Air: Doherty Hight Frequency 
		 Liquid: Transistor 12 current (/10 A) in amplifier 7"
	::= {amplifier7 23 }
	
	muteAmplifier7 OBJECT-TYPE
		SYNTAX Integer32
		MAX-ACCESS read-only
		STATUS current
		DESCRIPTION
			"Doherty muted by frequency error 
			    Muted (1),
				OK (2)"
	::= {amplifier7 24 }

--------------------------------------------------------
	amplifier8 OBJECT IDENTIFIER ::= { power 16 }

	pdAmplifier8 OBJECT-TYPE
		SYNTAX Integer32
		MAX-ACCESS read-only
		STATUS current
		DESCRIPTION
			"Output power (Watts) Amplifier 8"
	::= {amplifier8 1 }

	prAmplifier8 OBJECT-TYPE
		SYNTAX Integer32
		MAX-ACCESS read-only
		STATUS current
		DESCRIPTION
			"Reflected power (/10 Volts) Amplifier 8"
	::= {amplifier8 2 }

	pinAmplifier8 OBJECT-TYPE
		SYNTAX Integer32
		MAX-ACCESS read-only
		STATUS current
		DESCRIPTION
			"Input power (/10 Volts) Amplifier 8"
	::= {amplifier8 3 }

	temperatureAmplifier8 OBJECT-TYPE
		SYNTAX Integer32
		MAX-ACCESS read-only
		STATUS current
		DESCRIPTION
			"Temperature (C) Amplifier 8"
	::= {amplifier8 4 }

	vcagAmplifier8 OBJECT-TYPE
		SYNTAX Integer32
		MAX-ACCESS read-only
		STATUS current
		DESCRIPTION
			"CAG voltage (/10 Volts) Amplifier 8"
	::= {amplifier8 5 }

	vfaseAmplifier8 OBJECT-TYPE
		SYNTAX Integer32
		MAX-ACCESS read-only
		STATUS current
		DESCRIPTION
			"Fase voltage (/10 Volts) Amplifier 8"
	::= {amplifier8 6 }

	ipdrAmplifier8 OBJECT-TYPE
		SYNTAX Integer32
		MAX-ACCESS read-only
		STATUS current
		DESCRIPTION
			"Predriver current (/10 A) Amplifier 8"
	::= {amplifier8 7 }

	idrAmplifier8 OBJECT-TYPE
		SYNTAX Integer32
		MAX-ACCESS read-only
		STATUS current
		DESCRIPTION
			"Driver current (/10 A) Amplifier 8"
	::= {amplifier8 8 }

	it1Amplifier8 OBJECT-TYPE
		SYNTAX Integer32
		MAX-ACCESS read-only
		STATUS current
		DESCRIPTION
			"Transistor 1 current (/10 A) in Amplifier 8"
	::= {amplifier8 9 }

	it2Amplifier8 OBJECT-TYPE
		SYNTAX Integer32
		MAX-ACCESS read-only
		STATUS current
		DESCRIPTION
			"Transistor 2 current (/10 A) in Amplifier 8"
	::= {amplifier8 10 }

	it3Amplifier8 OBJECT-TYPE
		SYNTAX Integer32
		MAX-ACCESS read-only
		STATUS current
		DESCRIPTION
			"Transistor 3 current (/10 A) in Amplifier 8"
	::= {amplifier8 11 }

	it4Amplifier8 OBJECT-TYPE
		SYNTAX Integer32
		MAX-ACCESS read-only
		STATUS current
		DESCRIPTION
			"Transistor 4 current (/10 A) in Amplifier 8"
	::= {amplifier8 12 }

	it5Amplifier8 OBJECT-TYPE
		SYNTAX Integer32
		MAX-ACCESS read-only
		STATUS current
		DESCRIPTION
			"Transistor 5 current (/10 A) in Amplifier 8"
	::= {amplifier8 13 }

	it6Amplifier8 OBJECT-TYPE
		SYNTAX Integer32
		MAX-ACCESS read-only
		STATUS current
		DESCRIPTION
			"Transistor 6 current (/10 A) in Amplifier 8"
	::= {amplifier8 14 }

	it7Amplifier8 OBJECT-TYPE
		SYNTAX Integer32
		MAX-ACCESS read-only
		STATUS current
		DESCRIPTION
			"Transistor 7 current (/10 A) in Amplifier 8"
	::= {amplifier8 15 }

	it8Amplifier8 OBJECT-TYPE
		SYNTAX Integer32
		MAX-ACCESS read-only
		STATUS current
		DESCRIPTION
			"Transistor 8 current (/10 A) in Amplifier 8"
	::= {amplifier8 16 }

	it9IFAN1amplifier8 OBJECT-TYPE
		SYNTAX Integer32
		MAX-ACCESS read-only
		STATUS current
		DESCRIPTION
			"Transistor 9/ FAN 1 current (/10 A) in amplifier 8"
	::= {amplifier8 17 }

	it10IFAN2amplifier8 OBJECT-TYPE
		SYNTAX Integer32
		MAX-ACCESS read-only
		STATUS current
		DESCRIPTION
			"Transistor 10/ FAN 2 current (/10 A) in amplifier 8"
	::= {amplifier8 18 }

	faultPinAmplifier8 OBJECT-TYPE
		SYNTAX Integer32
		MAX-ACCESS read-only
		STATUS current
		DESCRIPTION
			"Fault Input Power Amplifier 8
				FAULT (1)
				OK (2)"
	::= {amplifier8 19 }

	faultVccAmplifier8 OBJECT-TYPE
		SYNTAX Integer32
		MAX-ACCESS read-only
		STATUS current
		DESCRIPTION
			"Faulty Power supply"
	::= {amplifier8 20 }
	
	futureUseAmplifier8 OBJECT-TYPE
		SYNTAX Integer32
		MAX-ACCESS read-only
		STATUS current
		DESCRIPTION
			"Doherty Optimal Channel Amplifier 8"
	::= {amplifier8 21 }
	
	it11amplifier8 OBJECT-TYPE
		SYNTAX Integer32
		MAX-ACCESS read-only
		STATUS current
		DESCRIPTION
			"Air: Doherty Low Frequency 
		 Liquid: Transistor 11 current (/10 A) in amplifier 8"
	::= {amplifier8 22 }
	
	it12amplifier8 OBJECT-TYPE
		SYNTAX Integer32
		MAX-ACCESS read-only
		STATUS current
		DESCRIPTION
			"Air: Doherty Hight Frequency 
		 Liquid: Transistor 12 current (/10 A) in amplifier 8"
	::= {amplifier8 23 }
	
	muteAmplifier8 OBJECT-TYPE
		SYNTAX Integer32
		MAX-ACCESS read-only
		STATUS current
		DESCRIPTION
			"Doherty muted by frequency error 
			    Muted (1),
				OK (2)"
	::= {amplifier8 24 }

--------------------------------------------------------
	amplifier9 OBJECT IDENTIFIER ::= { power 17 }

	pdamplifier9 OBJECT-TYPE
		SYNTAX Integer32
		MAX-ACCESS read-only
		STATUS current
		DESCRIPTION
			"Output power (Watts) Amplifier 9"
	::= {amplifier9 1 }

	pramplifier9 OBJECT-TYPE
		SYNTAX Integer32
		MAX-ACCESS read-only
		STATUS current
		DESCRIPTION
			"Reflected power (/10 Volts) Amplifier 9"
	::= {amplifier9 2 }

	pinamplifier9 OBJECT-TYPE
		SYNTAX Integer32
		MAX-ACCESS read-only
		STATUS current
		DESCRIPTION
			"Input power (/10 Volts) Amplifier 9"
	::= {amplifier9 3 }

	temperatureamplifier9 OBJECT-TYPE
		SYNTAX Integer32
		MAX-ACCESS read-only
		STATUS current
		DESCRIPTION
			"Temperature (C) Amplifier 9"
	::= {amplifier9 4 }

	vcagamplifier9 OBJECT-TYPE
		SYNTAX Integer32
		MAX-ACCESS read-only
		STATUS current
		DESCRIPTION
			"CAG voltage (/10 Volts) Amplifier 9"
	::= {amplifier9 5 }

	vfaseamplifier9 OBJECT-TYPE
		SYNTAX Integer32
		MAX-ACCESS read-only
		STATUS current
		DESCRIPTION
			"Fase voltage (/10 Volts) Amplifier 9"
	::= {amplifier9 6 }

	ipdramplifier9 OBJECT-TYPE
		SYNTAX Integer32
		MAX-ACCESS read-only
		STATUS current
		DESCRIPTION
			"Predriver current (/10 A) Amplifier 9"
	::= {amplifier9 7 }

	idramplifier9 OBJECT-TYPE
		SYNTAX Integer32
		MAX-ACCESS read-only
		STATUS current
		DESCRIPTION
			"Driver current (/10 A) Amplifier 9"
	::= {amplifier9 8 }

	it1amplifier9 OBJECT-TYPE
		SYNTAX Integer32
		MAX-ACCESS read-only
		STATUS current
		DESCRIPTION
			"Transistor 1 current (/10 A) in Amplifier 9"
	::= {amplifier9 9 }

	it2amplifier9 OBJECT-TYPE
		SYNTAX Integer32
		MAX-ACCESS read-only
		STATUS current
		DESCRIPTION
			"Transistor 2 current (/10 A) in Amplifier 9"
	::= {amplifier9 10 }

	it3amplifier9 OBJECT-TYPE
		SYNTAX Integer32
		MAX-ACCESS read-only
		STATUS current
		DESCRIPTION
			"Transistor 3 current (/10 A) in Amplifier 9"
	::= {amplifier9 11 }

	it4amplifier9 OBJECT-TYPE
		SYNTAX Integer32
		MAX-ACCESS read-only
		STATUS current
		DESCRIPTION
			"Transistor 4 current (/10 A) in Amplifier 9"
	::= {amplifier9 12 }

	it5amplifier9 OBJECT-TYPE
		SYNTAX Integer32
		MAX-ACCESS read-only
		STATUS current
		DESCRIPTION
			"Transistor 5 current (/10 A) in Amplifier 9"
	::= {amplifier9 13 }

	it6amplifier9 OBJECT-TYPE
		SYNTAX Integer32
		MAX-ACCESS read-only
		STATUS current
		DESCRIPTION
			"Transistor 6 current (/10 A) in Amplifier 9"
	::= {amplifier9 14 }

	it7amplifier9 OBJECT-TYPE
		SYNTAX Integer32
		MAX-ACCESS read-only
		STATUS current
		DESCRIPTION
			"Transistor 7 current (/10 A) in Amplifier 9"
	::= {amplifier9 15 }

	it8amplifier9 OBJECT-TYPE
		SYNTAX Integer32
		MAX-ACCESS read-only
		STATUS current
		DESCRIPTION
			"Transistor 8 current (/10 A) in Amplifier 9"
	::= {amplifier9 16 }

	it9IFAN1amplifier9 OBJECT-TYPE
		SYNTAX Integer32
		MAX-ACCESS read-only
		STATUS current
		DESCRIPTION
			"Transistor 9/ FAN 1 current (/10 A) in amplifier 9"
	::= {amplifier9 17 }

	it10IFAN2amplifier9 OBJECT-TYPE
		SYNTAX Integer32
		MAX-ACCESS read-only
		STATUS current
		DESCRIPTION
			"Transistor 10/ FAN 2 current (/10 A) in amplifier 9"
	::= {amplifier9 18 }

	faultPinamplifier9 OBJECT-TYPE
		SYNTAX Integer32
		MAX-ACCESS read-only
		STATUS current
		DESCRIPTION
			"Fault Input Power Amplifier 9
				FAULT (1)
				OK (2)"
	::= {amplifier9 19 }

	faultVccamplifier9 OBJECT-TYPE
		SYNTAX Integer32
		MAX-ACCESS read-only
		STATUS current
		DESCRIPTION
			"Faulty Power supply"
	::= {amplifier9 20 }
	
	futureUseAmplifier9 OBJECT-TYPE
		SYNTAX Integer32
		MAX-ACCESS read-only
		STATUS current
		DESCRIPTION
			"Doherty Optimal Channel Amplifier 9"
	::= {amplifier9 21 }
	
	it11amplifier9 OBJECT-TYPE
		SYNTAX Integer32
		MAX-ACCESS read-only
		STATUS current
		DESCRIPTION
			"Air: Doherty Low Frequency 
		 Liquid: Transistor 11 current (/10 A) in amplifier 9"
	::= {amplifier9 22 }
	
	it12amplifier9 OBJECT-TYPE
		SYNTAX Integer32
		MAX-ACCESS read-only
		STATUS current
		DESCRIPTION
			"Air: Doherty Hight Frequency 
		 Liquid: Transistor 12 current (/10 A) in amplifier 9"
	::= {amplifier9 23 }
	
	muteAmplifier9 OBJECT-TYPE
		SYNTAX Integer32
		MAX-ACCESS read-only
		STATUS current
		DESCRIPTION
			"Doherty muted by frequency error 
			    Muted (1),
				OK (2)"
	::= {amplifier9 24 }
	
	
	
--------------------------------------------------------
	amplifier10 OBJECT IDENTIFIER ::= { power 18 }

	pdamplifier10 OBJECT-TYPE
		SYNTAX Integer32
		MAX-ACCESS read-only
		STATUS current
		DESCRIPTION
			"Output power (Watts) Amplifier 10"
	::= {amplifier10 1 }

	pramplifier10 OBJECT-TYPE
		SYNTAX Integer32
		MAX-ACCESS read-only
		STATUS current
		DESCRIPTION
			"Reflected power (/10 Volts) Amplifier 10"
	::= {amplifier10 2 }

	pinamplifier10 OBJECT-TYPE
		SYNTAX Integer32
		MAX-ACCESS read-only
		STATUS current
		DESCRIPTION
			"Input power (/10 Volts) Amplifier 10"
	::= {amplifier10 3 }

	temperatureamplifier10 OBJECT-TYPE
		SYNTAX Integer32
		MAX-ACCESS read-only
		STATUS current
		DESCRIPTION
			"Temperature (C) Amplifier 10"
	::= {amplifier10 4 }

	vcagamplifier10 OBJECT-TYPE
		SYNTAX Integer32
		MAX-ACCESS read-only
		STATUS current
		DESCRIPTION
			"CAG voltage (/10 Volts) Amplifier 10"
	::= {amplifier10 5 }

	vfaseamplifier10 OBJECT-TYPE
		SYNTAX Integer32
		MAX-ACCESS read-only
		STATUS current
		DESCRIPTION
			"Fase voltage (/10 Volts) Amplifier 10"
	::= {amplifier10 6 }

	ipdramplifier10 OBJECT-TYPE
		SYNTAX Integer32
		MAX-ACCESS read-only
		STATUS current
		DESCRIPTION
			"Predriver current (/10 A) Amplifier 10"
	::= {amplifier10 7 }

	idramplifier10 OBJECT-TYPE
		SYNTAX Integer32
		MAX-ACCESS read-only
		STATUS current
		DESCRIPTION
			"Driver current (/10 A) Amplifier 10"
	::= {amplifier10 8 }

	it1amplifier10 OBJECT-TYPE
		SYNTAX Integer32
		MAX-ACCESS read-only
		STATUS current
		DESCRIPTION
			"Transistor 1 current (/10 A) in Amplifier 10"
	::= {amplifier10 9 }

	it2amplifier10 OBJECT-TYPE
		SYNTAX Integer32
		MAX-ACCESS read-only
		STATUS current
		DESCRIPTION
			"Transistor 2 current (/10 A) in Amplifier 10"
	::= {amplifier10 10 }

	it3amplifier10 OBJECT-TYPE
		SYNTAX Integer32
		MAX-ACCESS read-only
		STATUS current
		DESCRIPTION
			"Transistor 3 current (/10 A) in Amplifier 10"
	::= {amplifier10 11 }

	it4amplifier10 OBJECT-TYPE
		SYNTAX Integer32
		MAX-ACCESS read-only
		STATUS current
		DESCRIPTION
			"Transistor 4 current (/10 A) in Amplifier 10"
	::= {amplifier10 12 }

	it5amplifier10 OBJECT-TYPE
		SYNTAX Integer32
		MAX-ACCESS read-only
		STATUS current
		DESCRIPTION
			"Transistor 5 current (/10 A) in Amplifier 10"
	::= {amplifier10 13 }

	it6amplifier10 OBJECT-TYPE
		SYNTAX Integer32
		MAX-ACCESS read-only
		STATUS current
		DESCRIPTION
			"Transistor 6 current (/10 A) in Amplifier 10"
	::= {amplifier10 14 }

	it7amplifier10 OBJECT-TYPE
		SYNTAX Integer32
		MAX-ACCESS read-only
		STATUS current
		DESCRIPTION
			"Transistor 7 current (/10 A) in Amplifier 10"
	::= {amplifier10 15 }

	it8amplifier10 OBJECT-TYPE
		SYNTAX Integer32
		MAX-ACCESS read-only
		STATUS current
		DESCRIPTION
			"Transistor 8 current (/10 A) in Amplifier 10"
	::= {amplifier10 16 }

	it9IFAN1amplifier10 OBJECT-TYPE
		SYNTAX Integer32
		MAX-ACCESS read-only
		STATUS current
		DESCRIPTION
			"Transistor 9/ FAN 1 current (/10 A) in amplifier 10"
	::= {amplifier10 17 }

	it10IFAN2amplifier10 OBJECT-TYPE
		SYNTAX Integer32
		MAX-ACCESS read-only
		STATUS current
		DESCRIPTION
			"Transistor 10/ FAN 2 current (/10 A) in amplifier 10"
	::= {amplifier10 18 }

	faultPinamplifier10 OBJECT-TYPE
		SYNTAX Integer32
		MAX-ACCESS read-only
		STATUS current
		DESCRIPTION
			"Fault Input Power Amplifier 10
				FAULT (1)
				OK (2)"
	::= {amplifier10 19 }

	faultVccamplifier10 OBJECT-TYPE
		SYNTAX Integer32
		MAX-ACCESS read-only
		STATUS current
		DESCRIPTION
			"Faulty Power supply"
	::= {amplifier10 20 }
	
	futureUseAmplifier10 OBJECT-TYPE
		SYNTAX Integer32
		MAX-ACCESS read-only
		STATUS current
		DESCRIPTION
			"Doherty Optimal Channel Amplifier 10"
	::= {amplifier10 21 }
	
	it11amplifier10 OBJECT-TYPE
		SYNTAX Integer32
		MAX-ACCESS read-only
		STATUS current
		DESCRIPTION
			"Air: Doherty Low Frequency 
		 Liquid: Transistor 11 current (/10 A) in amplifier 10"
	::= {amplifier10 22 }
	
	it12amplifier10 OBJECT-TYPE
		SYNTAX Integer32
		MAX-ACCESS read-only
		STATUS current
		DESCRIPTION
			"Air: Doherty Hight Frequency 
		 Liquid: Transistor 12 current (/10 A) in amplifier 10"
	::= {amplifier10 23 }
	
	muteAmplifier10 OBJECT-TYPE
		SYNTAX Integer32
		MAX-ACCESS read-only
		STATUS current
		DESCRIPTION
			"Doherty muted by frequency error 
			    Muted (1),
				OK (2)"
	::= {amplifier10 24 }
	
--------------------------------------------------------
	amplifier11 OBJECT IDENTIFIER ::= { power 19 }

	pdamplifier11 OBJECT-TYPE
		SYNTAX Integer32
		MAX-ACCESS read-only
		STATUS current
		DESCRIPTION
			"Output power (Watts) Amplifier 11"
	::= {amplifier11 1 }

	pramplifier11 OBJECT-TYPE
		SYNTAX Integer32
		MAX-ACCESS read-only
		STATUS current
		DESCRIPTION
			"Reflected power (/10 Volts) Amplifier 11"
	::= {amplifier11 2 }

	pinamplifier11 OBJECT-TYPE
		SYNTAX Integer32
		MAX-ACCESS read-only
		STATUS current
		DESCRIPTION
			"Input power (/10 Volts) Amplifier 11"
	::= {amplifier11 3 }

	temperatureamplifier11 OBJECT-TYPE
		SYNTAX Integer32
		MAX-ACCESS read-only
		STATUS current
		DESCRIPTION
			"Temperature (C) Amplifier 11"
	::= {amplifier11 4 }

	vcagamplifier11 OBJECT-TYPE
		SYNTAX Integer32
		MAX-ACCESS read-only
		STATUS current
		DESCRIPTION
			"CAG voltage (/10 Volts) Amplifier 11"
	::= {amplifier11 5 }

	vfaseamplifier11 OBJECT-TYPE
		SYNTAX Integer32
		MAX-ACCESS read-only
		STATUS current
		DESCRIPTION
			"Fase voltage (/10 Volts) Amplifier 11"
	::= {amplifier11 6 }

	ipdramplifier11 OBJECT-TYPE
		SYNTAX Integer32
		MAX-ACCESS read-only
		STATUS current
		DESCRIPTION
			"Predriver current (/10 A) Amplifier 11"
	::= {amplifier11 7 }

	idramplifier11 OBJECT-TYPE
		SYNTAX Integer32
		MAX-ACCESS read-only
		STATUS current
		DESCRIPTION
			"Driver current (/10 A) Amplifier 11"
	::= {amplifier11 8 }

	it1amplifier11 OBJECT-TYPE
		SYNTAX Integer32
		MAX-ACCESS read-only
		STATUS current
		DESCRIPTION
			"Transistor 1 current (/10 A) in Amplifier 11"
	::= {amplifier11 9 }

	it2amplifier11 OBJECT-TYPE
		SYNTAX Integer32
		MAX-ACCESS read-only
		STATUS current
		DESCRIPTION
			"Transistor 2 current (/10 A) in Amplifier 11"
	::= {amplifier11 10 }

	it3amplifier11 OBJECT-TYPE
		SYNTAX Integer32
		MAX-ACCESS read-only
		STATUS current
		DESCRIPTION
			"Transistor 3 current (/10 A) in Amplifier 11"
	::= {amplifier11 11 }

	it4amplifier11 OBJECT-TYPE
		SYNTAX Integer32
		MAX-ACCESS read-only
		STATUS current
		DESCRIPTION
			"Transistor 4 current (/10 A) in Amplifier 11"
	::= {amplifier11 12 }

	it5amplifier11 OBJECT-TYPE
		SYNTAX Integer32
		MAX-ACCESS read-only
		STATUS current
		DESCRIPTION
			"Transistor 5 current (/10 A) in Amplifier 11"
	::= {amplifier11 13 }

	it6amplifier11 OBJECT-TYPE
		SYNTAX Integer32
		MAX-ACCESS read-only
		STATUS current
		DESCRIPTION
			"Transistor 6 curren t(/10 A) in Amplifier 11"
	::= {amplifier11 14 }

	it7amplifier11 OBJECT-TYPE
		SYNTAX Integer32
		MAX-ACCESS read-only
		STATUS current
		DESCRIPTION
			"Transistor 7 current (/10 A) in Amplifier 11"
	::= {amplifier11 15 }

	it8amplifier11 OBJECT-TYPE
		SYNTAX Integer32
		MAX-ACCESS read-only
		STATUS current
		DESCRIPTION
			"Transistor 8 current (/10 A) in Amplifier 11"
	::= {amplifier11 16 }

	it9IFAN1amplifier11 OBJECT-TYPE
		SYNTAX Integer32
		MAX-ACCESS read-only
		STATUS current
		DESCRIPTION
			"Transistor 9/ FAN 1 current (/10 A) in amplifier 11"
	::= {amplifier11 17 }

	it10IFAN2amplifier11 OBJECT-TYPE
		SYNTAX Integer32
		MAX-ACCESS read-only
		STATUS current
		DESCRIPTION
			"Transistor 10/ FAN 2 current (/10 A) in amplifier 11"
	::= {amplifier11 18 }

	faultPinamplifier11 OBJECT-TYPE
		SYNTAX Integer32
		MAX-ACCESS read-only
		STATUS current
		DESCRIPTION
			"Fault Input Power Amplifier 11
				FAULT (1)
				OK (2)"
	::= {amplifier11 19 }

	faultVccamplifier11 OBJECT-TYPE
		SYNTAX Integer32
		MAX-ACCESS read-only
		STATUS current
		DESCRIPTION
			"Faulty Power supply"
	::= {amplifier11 20 }
	
	
	futureUseAmplifier11 OBJECT-TYPE
		SYNTAX Integer32
		MAX-ACCESS read-only
		STATUS current
		DESCRIPTION
			"Doherty Optimal Channel Amplifier 11"
	::= {amplifier11 21 }
	
	it11amplifier11 OBJECT-TYPE
		SYNTAX Integer32
		MAX-ACCESS read-only
		STATUS current
		DESCRIPTION
			"Air: Doherty Low Frequency 
		 Liquid: Transistor 11 current (/10 A) in amplifier 11"
	::= {amplifier11 22 }
	
	it12amplifier11 OBJECT-TYPE
		SYNTAX Integer32
		MAX-ACCESS read-only
		STATUS current
		DESCRIPTION
			"Air: Doherty Hight Frequency 
		 Liquid: Transistor 12 current (/10 A) in amplifier 11"
	::= {amplifier11 23 }
	
	muteAmplifier11 OBJECT-TYPE
		SYNTAX Integer32
		MAX-ACCESS read-only
		STATUS current
		DESCRIPTION
			"Doherty muted by frequency error 
			    Muted (1),
				OK (2)"
	::= {amplifier11 24 }
--------------------------------------------------------
	amplifier12 OBJECT IDENTIFIER ::= { power 20 }

	pdamplifier12 OBJECT-TYPE
		SYNTAX Integer32
		MAX-ACCESS read-only
		STATUS current
		DESCRIPTION
			"Output power (Watts) Amplifier 12"
	::= {amplifier12 1 }

	pramplifier12 OBJECT-TYPE
		SYNTAX Integer32
		MAX-ACCESS read-only
		STATUS current
		DESCRIPTION
			"Reflected power (/10 Volts) Amplifier 12"
	::= {amplifier12 2 }

	pinamplifier12 OBJECT-TYPE
		SYNTAX Integer32
		MAX-ACCESS read-only
		STATUS current
		DESCRIPTION
			"Input power (/10 Volts) Amplifier 12"
	::= {amplifier12 3 }

	temperatureamplifier12 OBJECT-TYPE
		SYNTAX Integer32
		MAX-ACCESS read-only
		STATUS current
		DESCRIPTION
			"Temperature (C) Amplifier 12"
	::= {amplifier12 4 }

	vcagamplifier12 OBJECT-TYPE
		SYNTAX Integer32
		MAX-ACCESS read-only
		STATUS current
		DESCRIPTION
			"CAG voltage (/10 Volts) Amplifier 12"
	::= {amplifier12 5 }

	vfaseamplifier12 OBJECT-TYPE
		SYNTAX Integer32
		MAX-ACCESS read-only
		STATUS current
		DESCRIPTION
			"Fase voltage (/10 Volts) Amplifier 12"
	::= {amplifier12 6 }

	ipdramplifier12 OBJECT-TYPE
		SYNTAX Integer32
		MAX-ACCESS read-only
		STATUS current
		DESCRIPTION
			"Predriver current (/10 A) Amplifier 12"
	::= {amplifier12 7 }

	idramplifier12 OBJECT-TYPE
		SYNTAX Integer32
		MAX-ACCESS read-only
		STATUS current
		DESCRIPTION
			"Driver current (/10 A) Amplifier 12"
	::= {amplifier12 8 }

	it1amplifier12 OBJECT-TYPE
		SYNTAX Integer32
		MAX-ACCESS read-only
		STATUS current
		DESCRIPTION
			"Transistor 1 current (/10 A) in Amplifier 12"
	::= {amplifier12 9 }

	it2amplifier12 OBJECT-TYPE
		SYNTAX Integer32
		MAX-ACCESS read-only
		STATUS current
		DESCRIPTION
			"Transistor 2 current (/10 A) in Amplifier 12"
	::= {amplifier12 10 }

	it3amplifier12 OBJECT-TYPE
		SYNTAX Integer32
		MAX-ACCESS read-only
		STATUS current
		DESCRIPTION
			"Transistor 3 current (/10 A) in Amplifier 12"
	::= {amplifier12 11 }

	it4amplifier12 OBJECT-TYPE
		SYNTAX Integer32
		MAX-ACCESS read-only
		STATUS current
		DESCRIPTION
			"Transistor 4 current (/10 A) in Amplifier 12"
	::= {amplifier12 12 }

	it5amplifier12 OBJECT-TYPE
		SYNTAX Integer32
		MAX-ACCESS read-only
		STATUS current
		DESCRIPTION
			"Transistor 5 current (/10 A) in Amplifier 12"
	::= {amplifier12 13 }

	it6amplifier12 OBJECT-TYPE
		SYNTAX Integer32
		MAX-ACCESS read-only
		STATUS current
		DESCRIPTION
			"Transistor 6 current (/10 A) in Amplifier 12"
	::= {amplifier12 14 }

	it7amplifier12 OBJECT-TYPE
		SYNTAX Integer32
		MAX-ACCESS read-only
		STATUS current
		DESCRIPTION
			"Transistor 7 current (/10 A) in Amplifier 12"
	::= {amplifier12 15 }

	it8amplifier12 OBJECT-TYPE
		SYNTAX Integer32
		MAX-ACCESS read-only
		STATUS current
		DESCRIPTION
			"Transistor 8 current (/10 A) in Amplifier 12"
	::= {amplifier12 16 }

	it9IFAN1amplifier12 OBJECT-TYPE
		SYNTAX Integer32
		MAX-ACCESS read-only
		STATUS current
		DESCRIPTION
			"Transistor 9/ FAN 1 current (/10 A) in amplifier 12"
	::= {amplifier12 17 }

	it10IFAN2amplifier12 OBJECT-TYPE
		SYNTAX Integer32
		MAX-ACCESS read-only
		STATUS current
		DESCRIPTION
			"Transistor 10/ FAN 2 current (/10 A) in amplifier 12"
	::= {amplifier12 18 }

	faultPinamplifier12 OBJECT-TYPE
		SYNTAX Integer32
		MAX-ACCESS read-only
		STATUS current
		DESCRIPTION
			"Fault Input Power Amplifier 12
				FAULT (1)
				OK (2)"
	::= {amplifier12 19 }

	faultVccamplifier12 OBJECT-TYPE
		SYNTAX Integer32
		MAX-ACCESS read-only
		STATUS current
		DESCRIPTION
			"Faulty Power supply"
	::= {amplifier12 20 }
	
	futureUseAmplifier12 OBJECT-TYPE
		SYNTAX Integer32
		MAX-ACCESS read-only
		STATUS current
		DESCRIPTION
			"Doherty Optimal Channel Amplifier 12"
	::= {amplifier12 21 }
	
	it11amplifier12 OBJECT-TYPE
		SYNTAX Integer32
		MAX-ACCESS read-only
		STATUS current
		DESCRIPTION
			"Air: Doherty Low Frequency 
		 Liquid: Transistor 11 current (/10 A) in amplifier 12"
	::= {amplifier12 22 }
	
	it12amplifier12 OBJECT-TYPE
		SYNTAX Integer32
		MAX-ACCESS read-only
		STATUS current
		DESCRIPTION
			"Air: Doherty Hight Frequency 
		 Liquid: Transistor 12 current (/10 A) in amplifier 12"
	::= {amplifier12 23 }
	
	muteAmplifier12 OBJECT-TYPE
		SYNTAX Integer32
		MAX-ACCESS read-only
		STATUS current
		DESCRIPTION
			"Doherty muted by frequency error 
			    Muted (1),
				OK (2)"
	::= {amplifier12 24 }
	
--------------------------------------------------------
	amplifier13 OBJECT IDENTIFIER ::= { power 21 }

	pdamplifier13 OBJECT-TYPE
		SYNTAX Integer32
		MAX-ACCESS read-only
		STATUS current
		DESCRIPTION
			"Output power (Watts) Amplifier 13"
	::= {amplifier13 1 }

	pramplifier13 OBJECT-TYPE
		SYNTAX Integer32
		MAX-ACCESS read-only
		STATUS current
		DESCRIPTION
			"Reflected power (/10 Volts) Amplifier 13"
	::= {amplifier13 2 }

	pinamplifier13 OBJECT-TYPE
		SYNTAX Integer32
		MAX-ACCESS read-only
		STATUS current
		DESCRIPTION
			"Input power (/10 Volts) Amplifier 13"
	::= {amplifier13 3 }

	temperatureamplifier13 OBJECT-TYPE
		SYNTAX Integer32
		MAX-ACCESS read-only
		STATUS current
		DESCRIPTION
			"Temperature (C) Amplifier 13"
	::= {amplifier13 4 }

	vcagamplifier13 OBJECT-TYPE
		SYNTAX Integer32
		MAX-ACCESS read-only
		STATUS current
		DESCRIPTION
			"CAG voltage (/10 Volts) Amplifier 13"
	::= {amplifier13 5 }

	vfaseamplifier13 OBJECT-TYPE
		SYNTAX Integer32
		MAX-ACCESS read-only
		STATUS current
		DESCRIPTION
			"Fase voltage (/10 Volts) Amplifier 13"
	::= {amplifier13 6 }

	ipdramplifier13 OBJECT-TYPE
		SYNTAX Integer32
		MAX-ACCESS read-only
		STATUS current
		DESCRIPTION
			"Predriver current (/10 A) Amplifier 13"
	::= {amplifier13 7 }

	idramplifier13 OBJECT-TYPE
		SYNTAX Integer32
		MAX-ACCESS read-only
		STATUS current
		DESCRIPTION
			"Driver current (/10 A) Amplifier 13"
	::= {amplifier13 8 }

	it1amplifier13 OBJECT-TYPE
		SYNTAX Integer32
		MAX-ACCESS read-only
		STATUS current
		DESCRIPTION
			"Transistor 1 current (/10 A) in Amplifier 13"
	::= {amplifier13 9 }

	it2amplifier13 OBJECT-TYPE
		SYNTAX Integer32
		MAX-ACCESS read-only
		STATUS current
		DESCRIPTION
			"Transistor 2 current (/10 A) in Amplifier 13"
	::= {amplifier13 10 }

	it3amplifier13 OBJECT-TYPE
		SYNTAX Integer32
		MAX-ACCESS read-only
		STATUS current
		DESCRIPTION
			"Transistor 3 current (/10 A) in Amplifier 13"
	::= {amplifier13 11 }

	it4amplifier13 OBJECT-TYPE
		SYNTAX Integer32
		MAX-ACCESS read-only
		STATUS current
		DESCRIPTION
			"Transistor 4 current (/10 A) in Amplifier 13"
	::= {amplifier13 12 }

	it5amplifier13 OBJECT-TYPE
		SYNTAX Integer32
		MAX-ACCESS read-only
		STATUS current
		DESCRIPTION
			"Transistor 5 current (/10 A) in Amplifier 13"
	::= {amplifier13 13 }

	it6amplifier13 OBJECT-TYPE
		SYNTAX Integer32
		MAX-ACCESS read-only
		STATUS current
		DESCRIPTION
			"Transistor 6 current (/10 A) in Amplifier 13"
	::= {amplifier13 14 }

	it7amplifier13 OBJECT-TYPE
		SYNTAX Integer32
		MAX-ACCESS read-only
		STATUS current
		DESCRIPTION
			"Transistor 7 current (/10 A) in Amplifier 13"
	::= {amplifier13 15 }

	it8amplifier13 OBJECT-TYPE
		SYNTAX Integer32
		MAX-ACCESS read-only
		STATUS current
		DESCRIPTION
			"Transistor 8 current (/10 A) in Amplifier 13"
	::= {amplifier13 16 }

	it9IFAN1amplifier13 OBJECT-TYPE
		SYNTAX Integer32
		MAX-ACCESS read-only
		STATUS current
		DESCRIPTION
			"Transistor 9/ FAN 1 current (/10 A) in amplifier 13"
	::= {amplifier13 17 }

	it10IFAN2amplifier13 OBJECT-TYPE
		SYNTAX Integer32
		MAX-ACCESS read-only
		STATUS current
		DESCRIPTION
			"Transistor 10/ FAN 2 current (/10 A) in amplifier 13"
	::= {amplifier13 18 }

	faultPinamplifier13 OBJECT-TYPE
		SYNTAX Integer32
		MAX-ACCESS read-only
		STATUS current
		DESCRIPTION
			"Fault Input Power Amplifier 13
				FAULT (1)
				OK (2)"
	::= {amplifier13 19 }

	faultVccamplifier13 OBJECT-TYPE
		SYNTAX Integer32
		MAX-ACCESS read-only
		STATUS current
		DESCRIPTION
			"Faulty Power supply"
	::= {amplifier13 20 }
	
	futureUseAmplifier13 OBJECT-TYPE
		SYNTAX Integer32
		MAX-ACCESS read-only
		STATUS current
		DESCRIPTION
			"Doherty Optimal Channel Amplifier 13"
	::= {amplifier13 21 }
	
	it11amplifier13 OBJECT-TYPE
		SYNTAX Integer32
		MAX-ACCESS read-only
		STATUS current
		DESCRIPTION
			"Air: Doherty Low Frequency 
		 Liquid: Transistor 11 current (/10 A) in amplifier 13"
	::= {amplifier13 22 }
	
	it12amplifier13 OBJECT-TYPE
		SYNTAX Integer32
		MAX-ACCESS read-only
		STATUS current
		DESCRIPTION
			"Air: Doherty Hight Frequency 
		 Liquid: Transistor 12 current (/10 A) in amplifier 13"
	::= {amplifier13 23 }
	
	muteAmplifier13 OBJECT-TYPE
		SYNTAX Integer32
		MAX-ACCESS read-only
		STATUS current
		DESCRIPTION
			"Doherty muted by frequency error 
			    Muted (1),
				OK (2)"
	::= {amplifier13 24 }

--------------------------------------------------------
	amplifier14 OBJECT IDENTIFIER ::= { power 22 }

	pdamplifier14 OBJECT-TYPE
		SYNTAX Integer32
		MAX-ACCESS read-only
		STATUS current
		DESCRIPTION
			"Output power (Watts) Amplifier 14"
	::= {amplifier14 1 }

	pramplifier14 OBJECT-TYPE
		SYNTAX Integer32
		MAX-ACCESS read-only
		STATUS current
		DESCRIPTION
			"Reflected power (/10 Volts) Amplifier 14"
	::= {amplifier14 2 }

	pinamplifier14 OBJECT-TYPE
		SYNTAX Integer32
		MAX-ACCESS read-only
		STATUS current
		DESCRIPTION
			"Input power (/10 Volts) Amplifier 14"
	::= {amplifier14 3 }

	temperatureamplifier14 OBJECT-TYPE
		SYNTAX Integer32
		MAX-ACCESS read-only
		STATUS current
		DESCRIPTION
			"Temperature (C) Amplifier 14"
	::= {amplifier14 4 }

	vcagamplifier14 OBJECT-TYPE
		SYNTAX Integer32
		MAX-ACCESS read-only
		STATUS current
		DESCRIPTION
			"CAG voltage (/10 Volts) Amplifier 14"
	::= {amplifier14 5 }

	vfaseamplifier14 OBJECT-TYPE
		SYNTAX Integer32
		MAX-ACCESS read-only
		STATUS current
		DESCRIPTION
			"Fase voltage (/10 Volts) Amplifier 14"
	::= {amplifier14 6 }

	ipdramplifier14 OBJECT-TYPE
		SYNTAX Integer32
		MAX-ACCESS read-only
		STATUS current
		DESCRIPTION
			"Predriver current (/10 A) Amplifier 14"
	::= {amplifier14 7 }

	idramplifier14 OBJECT-TYPE
		SYNTAX Integer32
		MAX-ACCESS read-only
		STATUS current
		DESCRIPTION
			"Driver current (/10 A) Amplifier 14"
	::= {amplifier14 8 }

	it1amplifier14 OBJECT-TYPE
		SYNTAX Integer32
		MAX-ACCESS read-only
		STATUS current
		DESCRIPTION
			"Transistor 1 current (/10 A) in Amplifier 14"
	::= {amplifier14 9 }

	it2amplifier14 OBJECT-TYPE
		SYNTAX Integer32
		MAX-ACCESS read-only
		STATUS current
		DESCRIPTION
			"Transistor 2 current (/10 A) in Amplifier 14"
	::= {amplifier14 10 }

	it3amplifier14 OBJECT-TYPE
		SYNTAX Integer32
		MAX-ACCESS read-only
		STATUS current
		DESCRIPTION
			"Transistor 3 current (/10 A) in Amplifier 14"
	::= {amplifier14 11 }

	it4amplifier14 OBJECT-TYPE
		SYNTAX Integer32
		MAX-ACCESS read-only
		STATUS current
		DESCRIPTION
			"Transistor 4 current (/10 A) in Amplifier 14"
	::= {amplifier14 12 }

	it5amplifier14 OBJECT-TYPE
		SYNTAX Integer32
		MAX-ACCESS read-only
		STATUS current
		DESCRIPTION
			"Transistor 5 current (/10 A) in Amplifier 14"
	::= {amplifier14 13 }

	it6amplifier14 OBJECT-TYPE
		SYNTAX Integer32
		MAX-ACCESS read-only
		STATUS current
		DESCRIPTION
			"Transistor 6 current (/10 A) in Amplifier 14"
	::= {amplifier14 14 }

	it7amplifier14 OBJECT-TYPE
		SYNTAX Integer32
		MAX-ACCESS read-only
		STATUS current
		DESCRIPTION
			"Transistor 7 current (/10 A) in Amplifier 14"
	::= {amplifier14 15 }

	it8amplifier14 OBJECT-TYPE
		SYNTAX Integer32
		MAX-ACCESS read-only
		STATUS current
		DESCRIPTION
			"Transistor 8 current (/10 A) in Amplifier 14"
	::= {amplifier14 16 }

	it9IFAN1amplifier14 OBJECT-TYPE
		SYNTAX Integer32
		MAX-ACCESS read-only
		STATUS current
		DESCRIPTION
			"Transistor 9/ FAN 1 current (/10 A) in amplifier 14"
	::= {amplifier14 17 }

	it10IFAN2amplifier14 OBJECT-TYPE
		SYNTAX Integer32
		MAX-ACCESS read-only
		STATUS current
		DESCRIPTION
			"Transistor 10/ FAN 2 current (/10 A) in amplifier 14"
	::= {amplifier14 18 }

	faultPinamplifier14 OBJECT-TYPE
		SYNTAX Integer32
		MAX-ACCESS read-only
		STATUS current
		DESCRIPTION
			"Fault Input Power Amplifier 14
				FAULT (1)
				OK (2)"
	::= {amplifier14 19 }

	faultVccamplifier14 OBJECT-TYPE
		SYNTAX Integer32
		MAX-ACCESS read-only
		STATUS current
		DESCRIPTION
			"Faulty Power supply"
	::= {amplifier14 20 }
	
	futureUseAmplifier14 OBJECT-TYPE
		SYNTAX Integer32
		MAX-ACCESS read-only
		STATUS current
		DESCRIPTION
			"Doherty Optimal Channel Amplifier 14"
	::= {amplifier14 21 }
	
	it11amplifier14 OBJECT-TYPE
		SYNTAX Integer32
		MAX-ACCESS read-only
		STATUS current
		DESCRIPTION
			"Air: Doherty Low Frequency 
		 Liquid: Transistor 11 current(/10 A) in amplifier 14"
	::= {amplifier14 22 }
	
	it12amplifier14 OBJECT-TYPE
		SYNTAX Integer32
		MAX-ACCESS read-only
		STATUS current
		DESCRIPTION
			"Air: Doherty Hight Frequency 
		 Liquid: Transistor 12 current(/10 A) in amplifier 14"
	::= {amplifier14 23 }
	
	muteAmplifier14 OBJECT-TYPE
		SYNTAX Integer32
		MAX-ACCESS read-only
		STATUS current
		DESCRIPTION
			"Doherty muted by frequency error 
			    Muted (1),
				OK (2)"
	::= {amplifier14 24 }

--------------------------------------------------------
	amplifier15 OBJECT IDENTIFIER ::= { power 23 }

	pdamplifier15 OBJECT-TYPE
		SYNTAX Integer32
		MAX-ACCESS read-only
		STATUS current
		DESCRIPTION
			"Output power (Watts) Amplifier 15"
	::= {amplifier15 1 }

	pramplifier15 OBJECT-TYPE
		SYNTAX Integer32
		MAX-ACCESS read-only
		STATUS current
		DESCRIPTION
			"Reflected power (/10 Volts) Amplifier 15"
	::= {amplifier15 2 }

	pinamplifier15 OBJECT-TYPE
		SYNTAX Integer32
		MAX-ACCESS read-only
		STATUS current
		DESCRIPTION
			"Input power (/10 Volts) Amplifier 15"
	::= {amplifier15 3 }

	temperatureamplifier15 OBJECT-TYPE
		SYNTAX Integer32
		MAX-ACCESS read-only
		STATUS current
		DESCRIPTION
			"Temperature (C) Amplifier 15"
	::= {amplifier15 4 }

	vcagamplifier15 OBJECT-TYPE
		SYNTAX Integer32
		MAX-ACCESS read-only
		STATUS current
		DESCRIPTION
			"CAG voltage (/10 Volts) Amplifier 15"
	::= {amplifier15 5 }

	vfaseamplifier15 OBJECT-TYPE
		SYNTAX Integer32
		MAX-ACCESS read-only
		STATUS current
		DESCRIPTION
			"Fase voltage (/10 Volts) Amplifier 15"
	::= {amplifier15 6 }

	ipdramplifier15 OBJECT-TYPE
		SYNTAX Integer32
		MAX-ACCESS read-only
		STATUS current
		DESCRIPTION
			"Predriver current(/10 A)Amplifier 15"
	::= {amplifier15 7 }

	idramplifier15 OBJECT-TYPE
		SYNTAX Integer32
		MAX-ACCESS read-only
		STATUS current
		DESCRIPTION
			"Driver current (/10 A) Amplifier 15"
	::= {amplifier15 8 }

	it1amplifier15 OBJECT-TYPE
		SYNTAX Integer32
		MAX-ACCESS read-only
		STATUS current
		DESCRIPTION
			"Transistor 1 current (/10 A) in Amplifier 15"
	::= {amplifier15 9 }

	it2amplifier15 OBJECT-TYPE
		SYNTAX Integer32
		MAX-ACCESS read-only
		STATUS current
		DESCRIPTION
			"Transistor 2 current(/10 A) in Amplifier 15"
	::= {amplifier15 10 }

	it3amplifier15 OBJECT-TYPE
		SYNTAX Integer32
		MAX-ACCESS read-only
		STATUS current
		DESCRIPTION
			"Transistor 3 current (/10 A) in Amplifier 15"
	::= {amplifier15 11 }

	it4amplifier15 OBJECT-TYPE
		SYNTAX Integer32
		MAX-ACCESS read-only
		STATUS current
		DESCRIPTION
			"Transistor 4 current (/10 A) in Amplifier 15"
	::= {amplifier15 12 }

	it5amplifier15 OBJECT-TYPE
		SYNTAX Integer32
		MAX-ACCESS read-only
		STATUS current
		DESCRIPTION
			"Transistor 5 current (/10 A) in Amplifier 15"
	::= {amplifier15 13 }

	it6amplifier15 OBJECT-TYPE
		SYNTAX Integer32
		MAX-ACCESS read-only
		STATUS current
		DESCRIPTION
			"Transistor 6 current (/10 A) inAmplifier 15"
	::= {amplifier15 14 }

	it7amplifier15 OBJECT-TYPE
		SYNTAX Integer32
		MAX-ACCESS read-only
		STATUS current
		DESCRIPTION
			"Transistor 7 current (/10 A) in Amplifier 15"
	::= {amplifier15 15 }

	it8amplifier15 OBJECT-TYPE
		SYNTAX Integer32
		MAX-ACCESS read-only
		STATUS current
		DESCRIPTION
			"Transistor 8 current (/10 A) in Amplifier 15"
	::= {amplifier15 16 }

	it9IFAN1amplifier15 OBJECT-TYPE
		SYNTAX Integer32
		MAX-ACCESS read-only
		STATUS current
		DESCRIPTION
			"Transistor 9/ FAN 1 current (/10 A) in amplifier 15"
	::= {amplifier15 17 }

	it10IFAN2amplifier15 OBJECT-TYPE
		SYNTAX Integer32
		MAX-ACCESS read-only
		STATUS current
		DESCRIPTION
			"Transistor 10/ FAN 2 current (/10 A) in amplifier 15"
	::= {amplifier15 18 }

	faultPinamplifier15 OBJECT-TYPE
		SYNTAX Integer32
		MAX-ACCESS read-only
		STATUS current
		DESCRIPTION
			"Fault Input PowerAmplifier 15
				FAULT (1)
				OK (2)"
	::= {amplifier15 19 }

	faultVccamplifier15 OBJECT-TYPE
		SYNTAX Integer32
		MAX-ACCESS read-only
		STATUS current
		DESCRIPTION
			"Faulty Power supply"
	::= {amplifier15 20 }
	
	futureUseAmplifier15 OBJECT-TYPE
		SYNTAX Integer32
		MAX-ACCESS read-only
		STATUS current
		DESCRIPTION
			"Doherty Optimal Channel Amplifier 15"
	::= {amplifier15 21 }
	
	it11amplifier15 OBJECT-TYPE
		SYNTAX Integer32
		MAX-ACCESS read-only
		STATUS current
		DESCRIPTION
			"Air: Doherty Low Frequency 
		 Liquid: Transistor 11 current(/10 A) in amplifier 15"
	::= {amplifier15 22 }
	
	it12amplifier15 OBJECT-TYPE
		SYNTAX Integer32
		MAX-ACCESS read-only
		STATUS current
		DESCRIPTION
			"Air: Doherty Hight Frequency 
		 Liquid: Transistor 12 current(/10 A) in amplifier 15"
	::= {amplifier15 23 }
	
	muteAmplifier15 OBJECT-TYPE
		SYNTAX Integer32
		MAX-ACCESS read-only
		STATUS current
		DESCRIPTION
			"Doherty muted by frequency error 
			    Muted (1),
				OK (2)"
	::= {amplifier15 24 }

--------------------------------------------------------
	amplifier16 OBJECT IDENTIFIER ::= { power 24 }

	pdamplifier16 OBJECT-TYPE
		SYNTAX Integer32
		MAX-ACCESS read-only
		STATUS current
		DESCRIPTION
			"Output power (Watts) in Amplifier 16"
	::= {amplifier16 1 }

	pramplifier16 OBJECT-TYPE
		SYNTAX Integer32
		MAX-ACCESS read-only
		STATUS current
		DESCRIPTION
			"Reflected power (/10 Volts) in Amplifier 16"
	::= {amplifier16 2 }

	pinamplifier16 OBJECT-TYPE
		SYNTAX Integer32
		MAX-ACCESS read-only
		STATUS current
		DESCRIPTION
			"Input power(/10 Volts)Amplifier 16"
	::= {amplifier16 3 }

	temperatureamplifier16 OBJECT-TYPE
		SYNTAX Integer32
		MAX-ACCESS read-only
		STATUS current
		DESCRIPTION
			"Temperature (C) in Amplifier 16"
	::= {amplifier16 4 }

	vcagamplifier16 OBJECT-TYPE
		SYNTAX Integer32
		MAX-ACCESS read-only
		STATUS current
		DESCRIPTION
			"CAG voltage (/10 Volts) in Amplifier 16"
	::= {amplifier16 5 }

	vfaseamplifier16 OBJECT-TYPE
		SYNTAX Integer32
		MAX-ACCESS read-only
		STATUS current
		DESCRIPTION
			"Fase voltage (/10 Volts) in Amplifier 16"
	::= {amplifier16 6 }

	ipdramplifier16 OBJECT-TYPE
		SYNTAX Integer32
		MAX-ACCESS read-only
		STATUS current
		DESCRIPTION
			"Predriver current (/10 A)in Amplifier 16"
	::= {amplifier16 7 }

	idramplifier16 OBJECT-TYPE
		SYNTAX Integer32
		MAX-ACCESS read-only
		STATUS current
		DESCRIPTION
			"Driver current (/10 A) in Amplifier 16"
	::= {amplifier16 8 }

	it1amplifier16 OBJECT-TYPE
		SYNTAX Integer32
		MAX-ACCESS read-only
		STATUS current
		DESCRIPTION
			"Transistor 1 current(/10 A) in Amplifier 16"
	::= {amplifier16 9 }

	it2amplifier16 OBJECT-TYPE
		SYNTAX Integer32
		MAX-ACCESS read-only
		STATUS current
		DESCRIPTION
			"Transistor 2 current(/10 A) in Amplifier 16"
	::= {amplifier16 10 }

	it3amplifier16 OBJECT-TYPE
		SYNTAX Integer32
		MAX-ACCESS read-only
		STATUS current
		DESCRIPTION
			"Transistor 3 current(/10 A) in Amplifier 16"
	::= {amplifier16 11 }

	it4amplifier16 OBJECT-TYPE
		SYNTAX Integer32
		MAX-ACCESS read-only
		STATUS current
		DESCRIPTION
			"Transistor 4 current(/10 A) in Amplifier 16"
	::= {amplifier16 12 }

	it5amplifier16 OBJECT-TYPE
		SYNTAX Integer32
		MAX-ACCESS read-only
		STATUS current
		DESCRIPTION
			"Transistor 5 current(/10 A) in Amplifier 16"
	::= {amplifier16 13 }

	it6amplifier16 OBJECT-TYPE
		SYNTAX Integer32
		MAX-ACCESS read-only
		STATUS current
		DESCRIPTION
			"Transistor 6 current(/10 A) in Amplifier 16"
	::= {amplifier16 14 }

	it7amplifier16 OBJECT-TYPE
		SYNTAX Integer32
		MAX-ACCESS read-only
		STATUS current
		DESCRIPTION
			"Transistor 7 current(/10 A) in Amplifier 16"
	::= {amplifier16 15 }

	it8amplifier16 OBJECT-TYPE
		SYNTAX Integer32
		MAX-ACCESS read-only
		STATUS current
		DESCRIPTION
			"Transistor 8 current(/10 A) in Amplifier 16"
	::= {amplifier16 16 }

	it9IFAN1amplifier16 OBJECT-TYPE
		SYNTAX Integer32
		MAX-ACCESS read-only
		STATUS current
		DESCRIPTION
			"Transistor 9/ FAN 1 current (/10 A) in amplifier 16"
	::= {amplifier16 17 }

	it10IFAN2amplifier16 OBJECT-TYPE
		SYNTAX Integer32
		MAX-ACCESS read-only
		STATUS current
		DESCRIPTION
			"Transistor 10/ FAN 2 current (/10 A) in amplifier 16"
	::= {amplifier16 18 }

	faultPinamplifier16 OBJECT-TYPE
		SYNTAX Integer32
		MAX-ACCESS read-only
		STATUS current
		DESCRIPTION
			"Fault Input Power Amplifier 16
				FAULT (1)
				OK (2)"
	::= {amplifier16 19 }

	faultVccamplifier16 OBJECT-TYPE
		SYNTAX Integer32
		MAX-ACCESS read-only
		STATUS current
		DESCRIPTION
			"Faulty Power supply"
	::= {amplifier16 20 }
	
	futureUseAmplifier16 OBJECT-TYPE
		SYNTAX Integer32
		MAX-ACCESS read-only
		STATUS current
		DESCRIPTION
			"Doherty Optimal Channel Amplifier 16"
	::= {amplifier16 21 }
	
	it11amplifier16 OBJECT-TYPE
		SYNTAX Integer32
		MAX-ACCESS read-only
		STATUS current
		DESCRIPTION
			"Air: Doherty Low Frequency 
		 Liquid: Transistor 11 current(/10 A) in amplifier 16"
	::= {amplifier16 22 }
	
	it12amplifier16 OBJECT-TYPE
		SYNTAX Integer32
		MAX-ACCESS read-only
		STATUS current
		DESCRIPTION
			"Air: Doherty Hight Frequency 
		 Liquid: Transistor 12 current(/10 A) in amplifier 16"
	::= {amplifier16 23 }
	
	muteAmplifier16 OBJECT-TYPE
		SYNTAX Integer32
		MAX-ACCESS read-only
		STATUS current
		DESCRIPTION
			"Doherty muted by frequency error 
			    Muted (1),
				OK (2)"
	::= {amplifier16 24 }
		
	nIcc OBJECT-TYPE
		SYNTAX Integer32
		MAX-ACCESS read-only
		STATUS current
		DESCRIPTION
			"Amplifier number of transistors"
	::= { power 25 }
--------------------------------------------------------
	rack OBJECT IDENTIFIER ::= { singleDualDrive 2 }
		
	temperatureOutrack1 OBJECT-TYPE
		SYNTAX Integer32 (0..99)
		MAX-ACCESS read-only
		STATUS current
		DESCRIPTION
			"Rack temperature (C)"
	::= { rack 1 }
 		
	maxTemperature OBJECT-TYPE
  		SYNTAX Integer32 (0..99)
	    	MAX-ACCESS read-write
	    	STATUS current
	    	DESCRIPTION
     	   "Maximun rack temperature (C)"
 	::= { rack 2 }
 		
 	numTurbines OBJECT-TYPE
  		SYNTAX Integer32 (0..2)
	    	MAX-ACCESS read-write
	    	STATUS current
	    	DESCRIPTION
	        "Number of implemented turbines
	         Range: 0 - 2"
 	::= { rack 3 }
 		
 	turbineSwitchTime OBJECT-TYPE
  		SYNTAX Integer32 (0..9999)
	    	MAX-ACCESS read-write
	    	STATUS current
		DESCRIPTION
	        "Turbine switch time
	         Range: 0 - 9999 hours"
 	::= { rack 4 }
 		
 	turbineFailVref OBJECT-TYPE
	  SYNTAX Integer32 (0..100)
	  MAX-ACCESS read-only
	  STATUS current
	  DESCRIPTION
		  "%VREF on turbine failure
		   Range:0 to 100%"
	::= { rack 5 }

    turbineFailMuteTime OBJECT-TYPE
	  SYNTAX Integer32 (0..240)
	  MAX-ACCESS read-only
	  STATUS current
	  DESCRIPTION
		  "Time of cutoff after turbine failure.
		   Range: 0(no mute) to 240 hours"
	::= { rack 6 }
		  
	coolingSys OBJECT-TYPE
	  SYNTAX Integer32 (0..2)
	  MAX-ACCESS read-only
	  STATUS current
	  DESCRIPTION
		  "Cooling system
		  undefined (0),
		  Air (1),
		  Liquid (2)"
	::= { rack 7 }
	  
	maxFanSpeed OBJECT-TYPE
	  SYNTAX Integer32 (0..100)
	  MAX-ACCESS read-write
	  STATUS current
	  DESCRIPTION
		  "Maximum fan speed (0 to 100%)"
	::= { rack 8 }
	  
	antiFreezeMode OBJECT-TYPE
	  SYNTAX Integer32 (0..2)
	  MAX-ACCESS read-write
	  STATUS current
	  DESCRIPTION
		  "Anti-freeze mode:
		  undefined (0),
		  ON (1),
		  OFF (2)"
	::= { rack 9 }
	
	pressurerack1 OBJECT-TYPE
	  SYNTAX Integer32 
	  MAX-ACCESS read-only
	  STATUS current
	  DESCRIPTION
		  "Current measured pressure"
	::= { rack 10 }
		 
	flowCorrection OBJECT-TYPE
	  SYNTAX Integer32 (0..20)
	  MAX-ACCESS read-write
	  STATUS current
	  DESCRIPTION
		  "Flow Correction 0% to 20%"
	::= { rack 11 }
	
	serviceMode OBJECT-TYPE
	  SYNTAX Integer32 (0..2)
	  MAX-ACCESS read-write
	  STATUS current
	  DESCRIPTION
		  "Flow Correction 
		  undefined (0),
		  ON (1),
		  OFF (2)"
	::= { rack 12 }
	
	nomTemperature OBJECT-TYPE
		SYNTAX Integer32 (0..99)
		MAX-ACCESS read-only
		STATUS current
		DESCRIPTION
			"Nominal Temperature (C)"
	::= { rack 13 }
	
	exchangerFans OBJECT-TYPE
		SYNTAX Integer32 (1..2)
		MAX-ACCESS read-only
		STATUS current
		DESCRIPTION
			"Number of exchanger fans"
	::= { rack 14 }
	
	pump1RPMrack1 OBJECT-TYPE
		SYNTAX Integer32
		MAX-ACCESS read-only
		STATUS current
		DESCRIPTION
			"Pump 1 speed (RPM)"
	::= { rack 15 }
	
	pump1REFrack1 OBJECT-TYPE
		SYNTAX Integer32
		MAX-ACCESS read-only
		STATUS current
		DESCRIPTION
			"Pump 1 current work point reference (0-100%)"
	::= { rack 16 }
	
	pump1POWERrack1 OBJECT-TYPE
		SYNTAX Integer32
		MAX-ACCESS read-only
		STATUS current
		DESCRIPTION
			"Pump 1 Power consumption(W)"
	::= { rack 17 }
	
	pump1HEADrack1 OBJECT-TYPE
		SYNTAX Integer32
		MAX-ACCESS read-only
		STATUS current
		DESCRIPTION
			"Pump 1 Head (m)"
	::= { rack 18 }
	
	pump1TEMPrack1 OBJECT-TYPE
		SYNTAX Integer32
		MAX-ACCESS read-only
		STATUS current
		DESCRIPTION
			"Pump 1 liquid temperature (C)"
	::= { rack 19 }
	
	pump2RPMrack1 OBJECT-TYPE
		SYNTAX Integer32
		MAX-ACCESS read-only
		STATUS current
		DESCRIPTION
			"Pump 2 speed (RPM)"
	::= { rack 20 }
	
	pump2REFrack1 OBJECT-TYPE
		SYNTAX Integer32 (0..100)
		MAX-ACCESS read-only
		STATUS current
		DESCRIPTION
			"Pump 2 current work point reference (0-100%)"
	::= { rack 21 }
	
	pump2POWERrack1 OBJECT-TYPE
		SYNTAX Integer32
		MAX-ACCESS read-only
		STATUS current
		DESCRIPTION
			"Pump 2 Power consumption(W)"
	::= { rack 22 }
	
	pump2HEADrack1 OBJECT-TYPE
		SYNTAX Integer32
		MAX-ACCESS read-only
		STATUS current
		DESCRIPTION
			"Pump 2 Head (m)"
	::= { rack 23 }
	
	pump2TEMPrack1 OBJECT-TYPE
		SYNTAX Integer32
		MAX-ACCESS read-only
		STATUS current
		DESCRIPTION
			"Pump 2 liquid temperature (C)"
	::= { rack 24 }
	
	fan1RPMrack1 OBJECT-TYPE
		SYNTAX Integer32
		MAX-ACCESS read-only
		STATUS current
		DESCRIPTION
			"Exchanger fan 1 speed (RPM)"
	::= { rack 25 }
	
	fan1REFrack1 OBJECT-TYPE
		SYNTAX Integer32 (0..100)
		MAX-ACCESS read-only
		STATUS current
		DESCRIPTION
			"Exchanger fan 1 current work point reference (0-100%)"
	::= { rack 26 }
	
	fan2RPMrack1 OBJECT-TYPE
		SYNTAX Integer32
		MAX-ACCESS read-only
		STATUS current
		DESCRIPTION
			"Exchanger fan 2 speed (RPM)"
	::= { rack 27 }
	
	fan2REFrack1 OBJECT-TYPE
		SYNTAX Integer32
		MAX-ACCESS read-only
		STATUS current
		DESCRIPTION
			"Exchanger fan 2 current work point reference (0-100%)"
	::= { rack 28 }
		
	pressureHigh OBJECT-TYPE
	  SYNTAX Integer32 
	  MAX-ACCESS read-only
	  STATUS current
	  DESCRIPTION
		  "High pressure limit"
	::= { rack 29 }
	
	pressureLow OBJECT-TYPE
	  SYNTAX Integer32 
	  MAX-ACCESS read-only
	  STATUS current
	  DESCRIPTION
		  "Low pressure limit"
	::= { rack 30 }
	
	temperatureInrack1 OBJECT-TYPE
		SYNTAX Integer32 (0..99)
		MAX-ACCESS read-only
		STATUS current
		DESCRIPTION
			"Rack temperature (C)"
	::= { rack 31 }
	
	
	temperatureOutrack2 OBJECT-TYPE
		SYNTAX Integer32 (0..99)
		MAX-ACCESS read-only
		STATUS current
		DESCRIPTION
			"Rack temperature (C)"
	::= { rack 32 }
	
	pump1RPMrack2 OBJECT-TYPE
		SYNTAX Integer32
		MAX-ACCESS read-only
		STATUS current
		DESCRIPTION
			"Pump 1 speed (RPM)"
	::= { rack 33 }
	
	pressurerack2 OBJECT-TYPE
	  SYNTAX Integer32 
	  MAX-ACCESS read-only
	  STATUS current
	  DESCRIPTION
		  "Current measured pressure"
	::= { rack 34 }
		 
	
	pump1REFrack2 OBJECT-TYPE
		SYNTAX Integer32 (0..100)
		MAX-ACCESS read-only
		STATUS current
		DESCRIPTION
			"Pump 1 current work point reference (0-100%)"
	::= { rack 35 }
	
	pump1POWERrack2 OBJECT-TYPE
		SYNTAX Integer32
		MAX-ACCESS read-only
		STATUS current
		DESCRIPTION
			"Pump 1 Power consumption(W)"
	::= { rack 36 }
	
	pump1HEADrack2 OBJECT-TYPE
		SYNTAX Integer32
		MAX-ACCESS read-only
		STATUS current
		DESCRIPTION
			"Pump 1 Head (m)"
	::= { rack 37 }
	
	pump1TEMPrack2 OBJECT-TYPE
		SYNTAX Integer32
		MAX-ACCESS read-only
		STATUS current
		DESCRIPTION
			"Pump 1 liquid temperature (C)"
	::= { rack 38 }
	
	pump2RPMrack2 OBJECT-TYPE
		SYNTAX Integer32
		MAX-ACCESS read-only
		STATUS current
		DESCRIPTION
			"Pump 2 speed (RPM)"
	::= { rack 39 }
	
	pump2REFrack2 OBJECT-TYPE
		SYNTAX Integer32 (0..100)
		MAX-ACCESS read-only
		STATUS current
		DESCRIPTION
			"Pump 2 current work point reference (0-100%)"
	::= { rack 40 }
	
	pump2POWERrack2 OBJECT-TYPE
		SYNTAX Integer32
		MAX-ACCESS read-only
		STATUS current
		DESCRIPTION
			"Pump 2 Power consumption(W)"
	::= { rack 41 }
	
	pump2HEADrack2 OBJECT-TYPE
		SYNTAX Integer32
		MAX-ACCESS read-only
		STATUS current
		DESCRIPTION
			"Pump 2 Head (m)"
	::= { rack 42 }
	
	pump2TEMPrack2 OBJECT-TYPE
		SYNTAX Integer32
		MAX-ACCESS read-only
		STATUS current
		DESCRIPTION
			"Pump 2 liquid temperature (C)"
	::= { rack 43 }
	
	fan1RPMrack2 OBJECT-TYPE
		SYNTAX Integer32
		MAX-ACCESS read-only
		STATUS current
		DESCRIPTION
			"Exchanger fan 1 speed (RPM)"
	::= { rack 44 }
	
	fan1REFrack2 OBJECT-TYPE
		SYNTAX Integer32 (0..100)
		MAX-ACCESS read-only
		STATUS current
		DESCRIPTION
			"Exchanger fan 1 current work point reference (0-100%)"
	::= { rack 45 }
	
	fan2RPMrack2 OBJECT-TYPE
		SYNTAX Integer32
		MAX-ACCESS read-only
		STATUS current
		DESCRIPTION
			"Exchanger fan 2 speed (RPM)"
	::= { rack 46 }
	
	fan2REFrack2 OBJECT-TYPE
		SYNTAX Integer32 (0..100)
		MAX-ACCESS read-only
		STATUS current
		DESCRIPTION
			"Exchanger fan 2 current work point reference (0-100%)"
	::= { rack 47 }
	
	temperatureInrack2 OBJECT-TYPE
		SYNTAX Integer32 (0..99)
		MAX-ACCESS read-only
		STATUS current
		DESCRIPTION
			"Rack temperature (C)"
	::= { rack 48 }
	
	outputPowerrack1 OBJECT-TYPE
    		SYNTAX Integer32 
      	MAX-ACCESS read-only
      	STATUS current
      	DESCRIPTION
	        "Forward power rack 1(Watts)"
   	::= { rack 49 }
   	
   	outputPowerrack2 OBJECT-TYPE
    		SYNTAX Integer32 
      	MAX-ACCESS read-only
      	STATUS current
      	DESCRIPTION
	        "Forward power rack 2(Watts)"
   	::= { rack 50 }
   	
   	racksNumber OBJECT-TYPE
		SYNTAX Integer32
		MAX-ACCESS read-only
		STATUS current
		DESCRIPTION
			"Number of racks"
	::= { rack 51 }
----------------------------------------------------------
excA OBJECT IDENTIFIER ::= { singleDualDrive 3 }
		
	outputPowerexcA OBJECT-TYPE
    		SYNTAX DisplayString (SIZE (3))
      	MAX-ACCESS read-only
      	STATUS current
      	DESCRIPTION
	        "Exciter A output power (dBm)"
 	::= { excA 1 }
 		
 	channelexcA OBJECT-TYPE
    		SYNTAX Integer32
      	MAX-ACCESS read-only
      	STATUS current
      	DESCRIPTION
	        "Exciter A channel"
 	::= { excA 2 }
 		
 	tONexcA OBJECT-TYPE
  		SYNTAX Integer32 (0..120)
      	MAX-ACCESS read-write
      	STATUS current
      	DESCRIPTION
        	"Exciter A On time (1 to 120 seconds)"
	::= { excA 3 }
		
	excAModel OBJECT-TYPE
  		SYNTAX Integer32 (0..1)
      	MAX-ACCESS read-write
    		STATUS current
    		DESCRIPTION
      		"Exciter A model:
      			TDE9000 (0),
      			RED9000 (1)"
	::= { excA 4 }
----------------------------------------------------------
excB OBJECT IDENTIFIER ::= { singleDualDrive 4 }
		
	outputPowerexcB OBJECT-TYPE
    		SYNTAX DisplayString (SIZE (3))
      	MAX-ACCESS read-only
      	STATUS current
      	DESCRIPTION
	        "Exciter B output power (dBm)"
 	::= { excB 1 }
 		
 	channelexcB OBJECT-TYPE
    		SYNTAX Integer32
      	MAX-ACCESS read-only
      	STATUS current
      	DESCRIPTION
	        "Exciter B channel"
 	::= { excB 2 }
 		
 	tONexcB OBJECT-TYPE
    		SYNTAX Integer32 (0..120)
	     MAX-ACCESS read-write
      	STATUS current
      	DESCRIPTION
        	"Exciter B On time (1 to 120 seconds)"
	::= { excB 3 }
		
	excBModel OBJECT-TYPE
    		SYNTAX Integer32 
	     MAX-ACCESS read-write
      	STATUS current
      	DESCRIPTION
        	"Exciter B model:
        		TDE9000 (0),
        		RED9000 (1),
        		RS232 (2),
        		CONTACTS (3)"
	::= { excB 4 }
----------------------------------------------------------
configSDDD OBJECT IDENTIFIER ::= { singleDualDrive 5 }
		
	excOutPowerThreshold OBJECT-TYPE
    		SYNTAX DisplayString (SIZE (4))
	     MAX-ACCESS read-write
      	STATUS current
      	DESCRIPTION
        	"Exciter Output Power threshold (dBm)
        	 Format:(+/-)xxx"
	::= { configSDDD 1 }
		
	activeExciter OBJECT-TYPE
    		SYNTAX TruthValue 
	     MAX-ACCESS read-write
      	STATUS current
      	DESCRIPTION
        	"Active exciter 
        		Exciter A (1), 
        		Exciter B (2)"
	::= { configSDDD 2 }

	externalSwitch OBJECT-TYPE
    		SYNTAX TruthValue 
	     MAX-ACCESS read-only
      	STATUS current
      	DESCRIPTION
        	"External switch:
        		Antenna (1),
        		Load (2)"
	::= { configSDDD 3 }
		
----------------------------------------------------------
----------------------------------------------------------
ccu OBJECT IDENTIFIER ::= { ccu9000 3 }
		
    switchMode OBJECT-TYPE
    		SYNTAX TruthValue 
      	MAX-ACCESS read-write
      	STATUS current
      	DESCRIPTION
	        "Switch mode:
	        	Automatic (1),
	        	Manual (2)"
   	::= { ccu 1 }

     remoteLocal OBJECT-TYPE
    		SYNTAX TruthValue 
      	MAX-ACCESS read-write
      	STATUS current
      	DESCRIPTION
	        "CCU control mode:
	        	Local (1),
	        	Remote (2)"
   	::= { ccu 2 }

    ccuVariant OBJECT-TYPE
    		SYNTAX Integer32 
      	MAX-ACCESS read-only
      	STATUS current
      	DESCRIPTION
	        "CCU Variant:
	        	N+1 (0),
	        	Dual Drive (1),
	        	Single Drive (2)"
   	::= { ccu 3 }
   	
   	onoff OBJECT-TYPE
    		SYNTAX TruthValue 
      	MAX-ACCESS read-write
      	STATUS current
      	DESCRIPTION
	        "CCU Operation Mode: 
	        	ON (1),
	        	OFF (2)"
   	::= { ccu 4 }
   	
   	coldstartupT OBJECT-TYPE
    		SYNTAX Integer32 (0..300)
      	MAX-ACCESS read-write
      	STATUS current
      	DESCRIPTION
	        "Transmitter cold start time (0 to 300 s)"
   	::= { ccu 5 }

   	reset OBJECT-TYPE
    		SYNTAX TruthValue 
      	MAX-ACCESS read-write
      	STATUS current
      	DESCRIPTION
	        "Reset CCU: 
	        	Reset (1)"
   	::= { ccu 6 }
	
     time OBJECT-TYPE
    		SYNTAX DisplayString (SIZE (5))
      	MAX-ACCESS read-write
      	STATUS current
      	DESCRIPTION
	        "time format: XX:XX"
   	::= { ccu 7 }

     date OBJECT-TYPE
    		SYNTAX DisplayString (SIZE (5))
      	MAX-ACCESS read-write
      	STATUS current
      	DESCRIPTION
	        "date format: XX/XX"
   	::= { ccu 8 }

    ip1 OBJECT-TYPE
    		SYNTAX DisplayString (SIZE (15))
      	MAX-ACCESS read-write
      	STATUS current
      	DESCRIPTION
	        "Authorized IP 1 Format: XXX.XXX.XXX.XXX"
   	::= { ccu 9 }
   	
   	ip2 OBJECT-TYPE
    		SYNTAX DisplayString (SIZE (15))
      	MAX-ACCESS read-write
      	STATUS current
      	DESCRIPTION
	        "Authorized IP 2 Format: XXX.XXX.XXX.XXX"
   	::= { ccu 10 }
   	
   	ip3 OBJECT-TYPE
    		SYNTAX DisplayString (SIZE (15))
      	MAX-ACCESS read-write
      	STATUS current
      	DESCRIPTION
	        "Authorized IP 3 Format: XXX.XXX.XXX.XXX"
   	::= { ccu 11 }
   	
   	ip4 OBJECT-TYPE
    		SYNTAX DisplayString (SIZE (15))
      	MAX-ACCESS read-write
      	STATUS current
      	DESCRIPTION
	        "Authorized IP 4 Format: XXX.XXX.XXX.XXX"
   	::= { ccu 12 }

----------------------------------------------------------
----------------------------------------------------------
 gps OBJECT IDENTIFIER ::= { ccu9000 4 }

	gpsManagement OBJECT-TYPE
    		SYNTAX TruthValue 
      	MAX-ACCESS read-write
      	STATUS current
      	DESCRIPTION
	        "G.P.S. Management:
	        	ON (1),
	        	OFF (2)"
   	::= { gps 1 }

	gpsActive OBJECT-TYPE
    		SYNTAX TruthValue 
      	MAX-ACCESS read-only
      	STATUS current
      	DESCRIPTION
	        "G.P.S. active:  
	        	GPS A (1),
	        	GPS B (2)"
   	::= { gps 2 }

	gpsSatNumber OBJECT-TYPE
    		SYNTAX Integer32 (0..8)
      	MAX-ACCESS read-only
      	STATUS current
      	DESCRIPTION
	        "Number of tracked satellites (0 to 8)"
   	::= { gps 3 }
   	
----------------------------------------------------------
----------------------------------------------------------
    grouptx1 OBJECT-GROUP
    	OBJECTS 
    		{ 	
    			channel1, 
			outputPower1, 
			minPout1, 
			onoff1,
			priority1,
			tFault1,
			tON1,
			switchtx1,
			excModel1,
			faultwithWarn1,
			faultwithAlarm1,
			probeLevel1,
			probeThreshold1,
			localremote1
        }
      	STATUS current
      	DESCRIPTION 
        	"Transmitter 1 Group"
  	::= { mibGroups 1 }
  	
    grouptx2 OBJECT-GROUP
    	OBJECTS 
    		{ 	
    			channel2, 
  			outputPower2, 
  			minPout2, 
			onoff2,
			priority2,
			tFault2,
			tON2,
			switchtx2,
			excModel2,
			faultwithWarn2,
			faultwithAlarm2,
			probeLevel2,
			probeThreshold2,
			localremote2
       	}
      	STATUS current
      	DESCRIPTION 
        	"Transmitter 2 Group"
  	::= { mibGroups 2 }
  	
  	grouptx3 OBJECT-GROUP
    	OBJECTS 
    		{ 	
    			channel3, 
  			outputPower3, 
  			minPout3, 
			onoff3,
			priority3,
			tFault3,
			tON3,
			switchtx3,
			excModel3,
			faultwithWarn3,
			faultwithAlarm3,
			probeLevel3,
			probeThreshold3,
			localremote3
       	}
      	STATUS current
      	DESCRIPTION 
        	"Transmitter 3 Group"
  	::= { mibGroups 3 }
  	
	grouptx4 OBJECT-GROUP
    	OBJECTS 
    		{ 	
    			channel4, 
  			outputPower4, 
  			minPout4, 
			onoff4,
			priority4,
			tFault4,
			tON4,
			switchtx4,
			excModel4,
			faultwithWarn4,
			faultwithAlarm4,
			probeLevel4,
			probeThreshold4,
			localremote4
       	}
      	STATUS current
      	DESCRIPTION 
        	"Transmitter 4 Group"
  	::= { mibGroups 4 }  	
  	
 	grouptx5 OBJECT-GROUP
    	OBJECTS 
    		{ 	
    			channel5, 
  			outputPower5, 
  			minPout5, 
			onoff5,
			priority5,
			tFault5,
			tON5,
			switchtx5,
			excModel5,
			faultwithWarn5,
			faultwithAlarm5,
			probeLevel5,
			probeThreshold5,
			localremote5
       	}
      	STATUS current
      	DESCRIPTION 
        	"tx 5 Group"
  	::= { mibGroups 5 } 	
  	
	grouptx6 OBJECT-GROUP
    	OBJECTS 
    		{ 	
    			channel6, 
  			outputPower6, 
  			minPout6, 
			onoff6,
			priority6,
			tFault6,
			tON6,
			switchtx6,
			excModel6,
			faultwithWarn6,
			faultwithAlarm6,
			probeLevel6,
			probeThreshold6,
			localremote6
       	}
      	STATUS current
      	DESCRIPTION 
        	"Transmitter 6 Group"
  	::= { mibGroups 6 }  	
  	
 	grouptx7 OBJECT-GROUP
    	OBJECTS 
    		{
    			channel7, 
			outputPower7, 
			minPout7, 
			onoff7,
			priority7,
			tFault7,
			tON7,
			switchtx7,
			excModel7,
			faultwithWarn7,
			faultwithAlarm7,
			probeLevel7,
			probeThreshold7,
			localremote7
       	}
      	STATUS current
      	DESCRIPTION 
        	"Transmitter 7 Group"
  	::= { mibGroups 7 }
  	
	grouptx8 OBJECT-GROUP
    	OBJECTS 
    		{ 	
    			channel8, 
			outputPower8, 
			minPout8, 
			onoff8,
			priority8,
			tFault8,
			tON8,
			switchtx8,
			excModel8,
			faultwithWarn8,
			faultwithAlarm8,
			probeLevel8,
			probeThreshold8,
			localremote8
       	}
      	STATUS current
      	DESCRIPTION 
        	"Transmitter 8 Group"
  	::= { mibGroups 8 }  	
  	
  	grouptxR OBJECT-GROUP
    	OBJECTS 
    		{ 	
    			channelR, 
    			outputPowerR, 
			onoffR,
			tONR,
			switchRESET,
			excModelR,
			probeLevelR,
			probeThresholdR,
			localremoteR
         }
      	STATUS current
      	DESCRIPTION 
        	"Reserve Transmitter Group"
  	::= { mibGroups 9 }
  	
  	groupconfignplusone OBJECT-GROUP
    	OBJECTS 
    		{ 	
    			ntx, 
			autorestore,
			testAttempts,
			attemptInterval,
			testTime,
			testMode,
			testHour,
			restorationMaxNumber,
			attemptIntervalRestorations,
			txLoadTest,
			testPhase,
			testAttemptsExecuted,
			numberRestorationsTX1,
			numberRestorationsTX2,
			numberRestorationsTX3,
			numberRestorationsTX4,
			numberRestorationsTX5,
			numberRestorationsTX6,
			numberRestorationsTX7,
			numberRestorationsTX8
   		}
      	STATUS current
      	DESCRIPTION 
        	"N+1 Configuration Group"
  	::= { mibGroups 10 }
  	
	groupmatrix OBJECT-GROUP
    	OBJECTS 
    		{ 	
    			matrixActive, 
    			autoMan, 
    			asiSelect 
         }
      	STATUS current
      	DESCRIPTION 
        	"ASI Matrix Group"
  	::= { mibGroups 11 }

  	grouppower OBJECT-GROUP
    	OBJECTS 
    		{ 	
    			outputPower, 
    			reflectedPower, 
    			nominalPower,
    			minPowerThreshold,
    			maxReflectedThreshold,
    			powerControlRef,
    			commAmplifiers,
    			nAmplifiers,
    			cag
         }
      	STATUS current
      	DESCRIPTION 
        	"Power Group"
  	::= { mibGroups 12 }

    groupamplifier1 OBJECT-GROUP
	OBJECTS 
		{ 	
			pdAmplifier1,
			prAmplifier1,
			pinAmplifier1,
			temperatureAmplifier1,
			vcagAmplifier1,
			vfaseAmplifier1,
			ipdrAmplifier1,
			idrAmplifier1,
			it1Amplifier1,
			it2Amplifier1,
			it3Amplifier1,
			it4Amplifier1,
			it5Amplifier1,
			it6Amplifier1,
			it7Amplifier1,
			it8Amplifier1,
			it9IFAN1amplifier1,
			it10IFAN2amplifier1,
			faultPinAmplifier1,
			faultVccAmplifier1,
			futureUseAmplifier1,
			it11amplifier1,
			it12amplifier1,
			muteAmplifier1
		}
		STATUS current
		DESCRIPTION 
			"Amplifier 1 Group"
	::= { mibGroups 13 }

	groupamplifier2 OBJECT-GROUP
	OBJECTS 
		{ 	
			pdAmplifier2,
			prAmplifier2,
			pinAmplifier2,
			temperatureAmplifier2,
			vcagAmplifier2,
			vfaseAmplifier2,
			ipdrAmplifier2,
			idrAmplifier2,
			it1Amplifier2,
			it2Amplifier2,
			it3Amplifier2,
			it4Amplifier2,
			it5Amplifier2,
			it6Amplifier2,
			it7Amplifier2,
			it8Amplifier2,
			it9IFAN1amplifier2,
			it10IFAN2amplifier2,
			faultPinAmplifier2,
			faultVccAmplifier2,
			futureUseAmplifier2,
			it11amplifier2,
			it12amplifier2,
			muteAmplifier2
		}
		STATUS current
		DESCRIPTION 
			"Amplifier 2 Group"
	::= { mibGroups 14 }

	groupamplifier3 OBJECT-GROUP
	OBJECTS 
		{ 	
			pdAmplifier3,
			prAmplifier3,
			pinAmplifier3,
			temperatureAmplifier3,
			vcagAmplifier3,
			vfaseAmplifier3,
			ipdrAmplifier3,
			idrAmplifier3,
			it1Amplifier3,
			it2Amplifier3,
			it3Amplifier3,
			it4Amplifier3,
			it5Amplifier3,
			it6Amplifier3,
			it7Amplifier3,
			it8Amplifier3,
			it9IFAN1amplifier3,
			it10IFAN2amplifier3,
			faultPinAmplifier3,
			faultVccAmplifier3,
			futureUseAmplifier3,
			it11amplifier3,
			it12amplifier3,
			muteAmplifier3
		}
		STATUS current
		DESCRIPTION 
			"Amplifier 3 Group"
	::= { mibGroups 15 }

	groupamplifier4 OBJECT-GROUP
	OBJECTS 
		{ 	
			pdAmplifier4,
			prAmplifier4,
			pinAmplifier4,
			temperatureAmplifier4,
			vcagAmplifier4,
			vfaseAmplifier4,
			ipdrAmplifier4,
			idrAmplifier4,
			it1Amplifier4,
			it2Amplifier4,
			it3Amplifier4,
			it4Amplifier4,
			it5Amplifier4,
			it6Amplifier4,
			it7Amplifier4,
			it8Amplifier4,
			it9IFAN1amplifier4,
			it10IFAN2amplifier4,
			faultPinAmplifier4,
			faultVccAmplifier4,
			futureUseAmplifier4,
			it11amplifier4,
			it12amplifier4,
			muteAmplifier4
		}
		STATUS current
		DESCRIPTION 
			"Amplfier 4 Group"
	::= { mibGroups 16 }
  
  groupamplifier5 OBJECT-GROUP
	OBJECTS 
		{ 	
			pdAmplifier5,
			prAmplifier5,
			pinAmplifier5,
			temperatureAmplifier5,
			vcagAmplifier5,
			vfaseAmplifier5,
			ipdrAmplifier5,
			idrAmplifier5,
			it1Amplifier5,
			it2Amplifier5,
			it3Amplifier5,
			it4Amplifier5,
			it5Amplifier5,
			it6Amplifier5,
			it7Amplifier5,
			it8Amplifier5,
			it9IFAN1amplifier5,
			it10IFAN2amplifier5,
			faultPinAmplifier5,
			faultVccAmplifier5,
			futureUseAmplifier5,
			it11amplifier5,
			it12amplifier5,
			muteAmplifier5		
		}
		STATUS current
		DESCRIPTION 
			"Amplfier 5 Group"
	::= { mibGroups 17 }
  
  groupamplifier6 OBJECT-GROUP
	OBJECTS 
		{ 	
			pdAmplifier6,
			prAmplifier6,
			pinAmplifier6,
			temperatureAmplifier6,
			vcagAmplifier6,
			vfaseAmplifier6,
			ipdrAmplifier6,
			idrAmplifier6,
			it1Amplifier6,
			it2Amplifier6,
			it3Amplifier6,
			it4Amplifier6,
			it5Amplifier6,
			it6Amplifier6,
			it7Amplifier6,
			it8Amplifier6,
			it9IFAN1amplifier6,
			it10IFAN2amplifier6,
			faultPinAmplifier6,
			faultVccAmplifier6,
			futureUseAmplifier6,
			it11amplifier6,
			it12amplifier6,
			muteAmplifier6
		}
		STATUS current
		DESCRIPTION 
			"Amplfier 6 Group"
	::= { mibGroups 18 }
	
	groupamplifier7 OBJECT-GROUP
	OBJECTS 
		{ 	
			pdAmplifier7,
			prAmplifier7,
			pinAmplifier7,
			temperatureAmplifier7,
			vcagAmplifier7,
			vfaseAmplifier7,
			ipdrAmplifier7,
			idrAmplifier7,
			it1Amplifier7,
			it2Amplifier7,
			it3Amplifier7,
			it4Amplifier7,
			it5Amplifier7,
			it6Amplifier7,
			it7Amplifier7,
			it8Amplifier7,
			it9IFAN1amplifier7,
			it10IFAN2amplifier7,
			faultPinAmplifier7,
			faultVccAmplifier7,
			futureUseAmplifier7,
			it11amplifier7,
			it12amplifier7,
			muteAmplifier7
		}
		STATUS current
		DESCRIPTION 
			"Amplfier 7 Group"
	::= { mibGroups 19 }
	
	groupamplifier8 OBJECT-GROUP
	OBJECTS 
		{ 	
			pdAmplifier8,
			prAmplifier8,
			pinAmplifier8,
			temperatureAmplifier8,
			vcagAmplifier8,
			vfaseAmplifier8,
			ipdrAmplifier8,
			idrAmplifier8,
			it1Amplifier8,
			it2Amplifier8,
			it3Amplifier8,
			it4Amplifier8,
			it5Amplifier8,
			it6Amplifier8,
			it7Amplifier8,
			it8Amplifier8,
			it9IFAN1amplifier8,
			it10IFAN2amplifier8,
			faultPinAmplifier8,
			faultVccAmplifier8,
			futureUseAmplifier8,
			it11amplifier8,
			it12amplifier8,
			muteAmplifier8
		}
		STATUS current
		DESCRIPTION 
			"Amplfier 8 Group"
	::= { mibGroups 20 }
	
	groupamplifier9 OBJECT-GROUP
	OBJECTS 
		{ 	
			pdamplifier9,
			pramplifier9,
			pinamplifier9,
			temperatureamplifier9,
			vcagamplifier9,
			vfaseamplifier9,
			ipdramplifier9,
			idramplifier9,
			it1amplifier9,
			it2amplifier9,
			it3amplifier9,
			it4amplifier9,
			it5amplifier9,
			it6amplifier9,
			it7amplifier9,
			it8amplifier9,
			it9IFAN1amplifier9,
			it10IFAN2amplifier9,
			faultPinamplifier9,
			faultVccamplifier9,
			futureUseAmplifier9,
			it11amplifier9,
			it12amplifier9,
			muteAmplifier9
		}
		STATUS current
		DESCRIPTION 
			"Amplfier 9 Group"
	::= { mibGroups 21 }
	
	groupamplifier10 OBJECT-GROUP
	OBJECTS 
		{ 	
			pdamplifier10,
			pramplifier10,
			pinamplifier10,
			temperatureamplifier10,
			vcagamplifier10,
			vfaseamplifier10,
			ipdramplifier10,
			idramplifier10,
			it1amplifier10,
			it2amplifier10,
			it3amplifier10,
			it4amplifier10,
			it5amplifier10,
			it6amplifier10,
			it7amplifier10,
			it8amplifier10,
			it9IFAN1amplifier10,
			it10IFAN2amplifier10,
			faultPinamplifier10,
			faultVccamplifier10,
			futureUseAmplifier10,
			it11amplifier10,
			it12amplifier10,
			muteAmplifier10
		}
		STATUS current
		DESCRIPTION 
			"Amplfier 10 Group"
	::= { mibGroups 22 }
	
	groupamplifier11 OBJECT-GROUP
	OBJECTS 
		{ 	
			pdamplifier11,
			pramplifier11,
			pinamplifier11,
			temperatureamplifier11,
			vcagamplifier11,
			vfaseamplifier11,
			ipdramplifier11,
			idramplifier11,
			it1amplifier11,
			it2amplifier11,
			it3amplifier11,
			it4amplifier11,
			it5amplifier11,
			it6amplifier11,
			it7amplifier11,
			it8amplifier11,
			it9IFAN1amplifier11,
			it10IFAN2amplifier11,
			faultPinamplifier11,
			faultVccamplifier11,
			futureUseAmplifier11,
			it11amplifier11,
			it12amplifier11,
			muteAmplifier11
		}
		STATUS current
		DESCRIPTION 
			"Amplfier 11 Group"
	::= { mibGroups 23 }
	
	groupamplifier12 OBJECT-GROUP
	OBJECTS 
		{ 	
			pdamplifier12,
			pramplifier12,
			pinamplifier12,
			temperatureamplifier12,
			vcagamplifier12,
			vfaseamplifier12,
			ipdramplifier12,
			idramplifier12,
			it1amplifier12,
			it2amplifier12,
			it3amplifier12,
			it4amplifier12,
			it5amplifier12,
			it6amplifier12,
			it7amplifier12,
			it8amplifier12,
			it9IFAN1amplifier12,
			it10IFAN2amplifier12,
			faultPinamplifier12,
			faultVccamplifier12,
			futureUseAmplifier12,
			it11amplifier12,
			it12amplifier12,
			muteAmplifier12
		}
		STATUS current
		DESCRIPTION 
			"Amplfier 12 Group"
	::= { mibGroups 24 }
	
	groupamplifier13 OBJECT-GROUP
	OBJECTS 
		{ 	
			pdamplifier13,
			pramplifier13,
			pinamplifier13,
			temperatureamplifier13,
			vcagamplifier13,
			vfaseamplifier13,
			ipdramplifier13,
			idramplifier13,
			it1amplifier13,
			it2amplifier13,
			it3amplifier13,
			it4amplifier13,
			it5amplifier13,
			it6amplifier13,
			it7amplifier13,
			it8amplifier13,
			it9IFAN1amplifier13,
			it10IFAN2amplifier13,
			faultPinamplifier13,
			faultVccamplifier13,
			futureUseAmplifier13,
			it11amplifier13,
			it12amplifier13,
			muteAmplifier13
		}
		STATUS current
		DESCRIPTION 
			"Amplfier 13 Group"
	::= { mibGroups 25 }
	
	groupamplifier14 OBJECT-GROUP
	OBJECTS 
		{ 	
			pdamplifier14,
			pramplifier14,
			pinamplifier14,
			temperatureamplifier14,
			vcagamplifier14,
			vfaseamplifier14,
			ipdramplifier14,
			idramplifier14,
			it1amplifier14,
			it2amplifier14,
			it3amplifier14,
			it4amplifier14,
			it5amplifier14,
			it6amplifier14,
			it7amplifier14,
			it8amplifier14,
			it9IFAN1amplifier14,
			it10IFAN2amplifier14,
			faultPinamplifier14,
			faultVccamplifier14,
			futureUseAmplifier14,
			it11amplifier14,
			it12amplifier14,
			muteAmplifier14
		}
		STATUS current
		DESCRIPTION 
			"Amplfier 14 Group"
	::= { mibGroups 26 }
	
	groupamplifier15 OBJECT-GROUP
	OBJECTS 
		{ 	
			pdamplifier15,
			pramplifier15,
			pinamplifier15,
			temperatureamplifier15,
			vcagamplifier15,
			vfaseamplifier15,
			ipdramplifier15,
			idramplifier15,
			it1amplifier15,
			it2amplifier15,
			it3amplifier15,
			it4amplifier15,
			it5amplifier15,
			it6amplifier15,
			it7amplifier15,
			it8amplifier15,
			it9IFAN1amplifier15,
			it10IFAN2amplifier15,
			faultPinamplifier15,
			faultVccamplifier15,
			futureUseAmplifier15,
			it11amplifier15,
			it12amplifier15,
			muteAmplifier15
		}
		STATUS current
		DESCRIPTION 
			"Amplfier 15 Group"
	::= { mibGroups 27 }
	
	groupamplifier16 OBJECT-GROUP
	OBJECTS 
		{ 	
			pdamplifier16,
			pramplifier16,
			pinamplifier16,
			temperatureamplifier16,
			vcagamplifier16,
			vfaseamplifier16,
			ipdramplifier16,
			idramplifier16,
			it1amplifier16,
			it2amplifier16,
			it3amplifier16,
			it4amplifier16,
			it5amplifier16,
			it6amplifier16,
			it7amplifier16,
			it8amplifier16,
			it9IFAN1amplifier16,
			it10IFAN2amplifier16,
			faultPinamplifier16,
			faultVccamplifier16,
			futureUseAmplifier16,
			it11amplifier16,
			it12amplifier16,
			muteAmplifier16
		}
		STATUS current
		DESCRIPTION 
			"Amplfier 16 Group"
	::= { mibGroups 28 }
	
 	grouprack OBJECT-GROUP
 	OBJECTS 
 		{ 	
 			temperatureOutrack1, 
			maxTemperature, 
			numTurbines,
			turbineSwitchTime,
			turbineFailVref,
			turbineFailMuteTime,
			coolingSys,
			maxFanSpeed,
			antiFreezeMode,
			pressurerack1,
			flowCorrection,
			serviceMode,
			nomTemperature,
			exchangerFans,
			pump1RPMrack1,
			pump1REFrack1,
			pump1POWERrack1,
			pump1HEADrack1,
			pump1TEMPrack1,
			pump2RPMrack1,
			pump2REFrack1,
			pump2POWERrack1,
			pump2HEADrack1,
			pump2TEMPrack1,
			fan1RPMrack1,
			fan1REFrack1,
			fan2RPMrack1,
			fan2REFrack1,
			pressureHigh,
			pressureLow,
			temperatureInrack1,
			temperatureOutrack2,
			pressurerack2,
			pump1RPMrack2,
			pump1REFrack2,
			pump1POWERrack2,
			pump1HEADrack2,
			pump1TEMPrack2,
			pump2RPMrack2,
			pump2REFrack2,
			pump2POWERrack2,
			pump2HEADrack2,
			pump2TEMPrack2,
			fan1RPMrack2,
			fan1REFrack2,
			fan2RPMrack2,
			fan2REFrack2,
			temperatureInrack2,
			outputPowerrack1,
			outputPowerrack2,
			racksNumber
 		}
   	STATUS current
   	DESCRIPTION 
     	"Rack parameters Group"
 	::= { mibGroups 29 }
  	
 	groupexcA OBJECT-GROUP
 	OBJECTS 
 		{ 	
 			outputPowerexcA, 
 			channelexcA, 
 			tONexcA,
 			excAModel
    }
   	STATUS current
   	DESCRIPTION 
    	"Exciter A Group"
 	::= { mibGroups 30 }
  	
 	groupexcB OBJECT-GROUP
 	OBJECTS 
 		{ 	
 			outputPowerexcB, 
 			channelexcB, 
 			tONexcB,
 			excBModel
    }
   	STATUS current
   	DESCRIPTION 
     	"Exciter B Group"
 	::= { mibGroups 31 }
  	
 	groupconfigSDDD OBJECT-GROUP
 	OBJECTS 
 		{ 	
 			excOutPowerThreshold, 
 			activeExciter,
			externalSwitch
    }
    STATUS current
    DESCRIPTION 
     	"Single and Dual dual drive configuration Group"
  ::= { mibGroups 32 }
  	
  groupccu OBJECT-GROUP
  OBJECTS 
  	{ 	
  		switchMode, 
			remoteLocal, 
			ccuVariant,
			onoff,
			coldstartupT,
			reset,
			time,
			date,
			ip1,
			ip2,
			ip3,
			ip4
  	}
   	STATUS current
   	DESCRIPTION 
     	"CCU configuration Group"
  ::= { mibGroups 33 }
  	
  groupgps OBJECT-GROUP
  OBJECTS 
  	{ 	
  		gpsManagement, 
  		gpsActive, 
  		gpsSatNumber 
    }
   	STATUS current
   	DESCRIPTION 
     	"GPS Group"
  ::= { mibGroups 34 }
  	
  groupNotifications NOTIFICATION-GROUP
	NOTIFICATIONS	
		{	
			inputFailure1, 	
			referenceFailure1,
			ppsFailure1,
			warningFailure1,
			sumfaultFailure1,
			noResponseFailure1,
			antennaLoadFailure1,
			poutFailure1,
			coaxialswitchFailure1,
			inputFailure2, 	
			referenceFailure2,
			ppsFailure2,
			warningFailure2,
			sumfaultFailure2,
			noResponseFailure2,
			antennaLoadFailure2,
			poutFailure2,
			coaxialswitchFailure2,
			inputFailure3, 	
			referenceFailure3,
			ppsFailure3,
			warningFailure3,
			sumfaultFailure3,
			noResponseFailure3,
			antennaLoadFailure3,
			poutFailure3,
			coaxialswitchFailure3,
			inputFailure4, 	
			referenceFailure4,
			ppsFailure4,
			warningFailure4,
			sumfaultFailure4,
			noResponseFailure4,
			antennaLoadFailure4,
			poutFailure4,
			coaxialswitchFailure4,
			inputFailure5, 	
			referenceFailure5,
			ppsFailure5,
			warningFailure5,
			sumfaultFailure5,
			noResponseFailure5,
			antennaLoadFailure5,
			poutFailure5,
			coaxialswitchFailure5,
			inputFailure6, 	
			referenceFailure6,
			ppsFailure6,
			warningFailure6,
			sumfaultFailure6,
			noResponseFailure6,
			antennaLoadFailure6,
			poutFailure6,
			coaxialswitchFailure6,
			inputFailure7, 	
			referenceFailure7,
			ppsFailure7,
			warningFailure7,
			sumfaultFailure7,
			noResponseFailure7,
			antennaLoadFailure7,
			poutFailure7,
			coaxialswitchFailure7,
			inputFailure8, 	
			referenceFailure8,
			ppsFailure8,
			warningFailure8,
			sumfaultFailure8,
			noResponseFailure8,
			antennaLoadFailure8,
			poutFailure8,
			coaxialswitchFailure8,
			inputFailureR, 	
			referenceFailureR,
			ppsFailureR,
			warningFailureR,
			sumfaultFailureR,
			noResponseFailureR,
			antennaLoadFailureR,
			poutFailureR,
			noResponseMatrix,
			poutFailure,
			reflectedFailure,
			temperatureFailure,
			turbine1,
			turbine2,
			coaxialswitch,
			amplifier,
			powersupply,
			flow1Faultrack1,
			flow2Faultrack1,
			pumpsLinkrack1,
			secLooprack1,
			mainLooprack1,
			auxPowerrack1,
			coolingrack1,
			pressureFaultrack1,
			coolingPowerrack1,
			exchangeFan1Comrack1,
			exchangeFan2Comrack1,
			pump1Faultrack1,
			pump2Faultrack1,
			exchangeFan1Faultrack1,
			exchangeFan2Faultrack1,
			exchangeLinkrack1,
			exchangePowerrack1,
			pump1Linkrack1,
			pump2Linkrack1,
			flow1Faultrack2,
			flow2Faultrack2,
			pumpsLinkrack2,
			secLooprack2,
			mainLooprack2,
			auxPowerrack2,
			coolingrack2,
			pressureFaultrack2,
			coolingPowerrack2,
			exchangeFan1Comrack2,
			exchangeFan2Comrack2,
			pump1Faultrack2,
			pump2Faultrack2,
			exchangeFan1Faultrack2,
			exchangeFan2Faultrack2,
			exchangeLinkrack2,
			exchangePowerrack2,
			pump1Linkrack2,
			pump2Linkrack2,
			inputexcA,
			referenceexcA,
			ppsexcA,
			warningexcA,
			faultexcA,
			outputPowerexcAFailure,
			noResponseexcA,
			antennaLoadexcA,
			inputexcB,
			referenceexcB,
			ppsexcB,
			warningexcB,
			faultexcB,
			outputPowerexcBFailure,
			noResponseexcB,
			antennaLoadexcB,
			switchSystemReady,
			ccuFault,
			interlockFailure,
			gpslockAnotification,
			sfnreadyAnotification,
			vccAnotification,
			gpslockBnotification,
			sfnreadyBnotification,
			vccBnotification,
			warningGPS,
			faultGPS,
			noResponseGPS
		}
		STATUS current     
		DESCRIPTION
			"Notifications Group"
	::= {mibGroups 35}

	groupEnableNotifications OBJECT-GROUP
	OBJECTS 
		{ 			
     		enableinputFailure1, 	
			enablereferenceFailure1,
			enableppsFailure1,
			enablewarningFailure1,
			enablesumfaultFailure1,
			enablenoResponseFailure1,
			enableantennaLoadFailure1,
			enablepoutFailure1,
			enablecoaxialswitchFailure1,
			enableinputFailure2, 	
			enablereferenceFailure2,
			enableppsFailure2,
			enablewarningFailure2,
			enablesumfaultFailure2,
			enablenoResponseFailure2,
			enableantennaLoadFailure2,
			enablepoutFailure2,
			enablecoaxialswitchFailure2,
			enableinputFailure3, 	
			enablereferenceFailure3,
			enableppsFailure3,
			enablewarningFailure3,
			enablesumfaultFailure3,
			enablenoResponseFailure3,
			enableantennaLoadFailure3,
			enablepoutFailure3,
			enablecoaxialswitchFailure3,
			enableinputFailure4, 	
			enablereferenceFailure4,
			enableppsFailure4,
			enablewarningFailure4,
			enablesumfaultFailure4,
			enablenoResponseFailure4,
			enableantennaLoadFailure4,
			enablepoutFailure4,
			enablecoaxialswitchFailure4,
			enableinputFailure5, 	
			enablereferenceFailure5,
			enableppsFailure5,
			enablewarningFailure5,
			enablesumfaultFailure5,
			enablenoResponseFailure5,
			enableantennaLoadFailure5,
			enablepoutFailure5,
			enablecoaxialswitchFailure5,
			enableinputFailure6, 	
			enablereferenceFailure6,
			enableppsFailure6,
			enablewarningFailure6,
			enablesumfaultFailure6,
			enablenoResponseFailure6,
			enableantennaLoadFailure6,
			enablepoutFailure6,
			enablecoaxialswitchFailure6,
			enableinputFailure7, 	
			enablereferenceFailure7,
			enableppsFailure7,
			enablewarningFailure7,
			enablesumfaultFailure7,
			enablenoResponseFailure7,
			enableantennaLoadFailure7,
			enablepoutFailure7,
			enablecoaxialswitchFailure7,
			enableinputFailure8, 	
			enablereferenceFailure8,
			enableppsFailure8,
			enablewarningFailure8,
			enablesumfaultFailure8,
			enablenoResponseFailure8,
			enableantennaLoadFailure8,
			enablepoutFailure8,
			enablecoaxialswitchFailure8,
			enableinputFailureR, 	
			enablereferenceFailureR,
			enableppsFailureR,
			enablewarningFailureR,
			enablesumfaultFailureR,
			enablenoResponseFailureR,
			enableantennaLoadFailureR,
			enablepoutFailureR,
			enablenoResponseMatrix,
			enablepoutFailure,
			enablereflectedFailure,
			enabletemperatureFailure,
			enableturbine1,
			enableturbine2,
			enablecoaxialswitch,
			enableamplifier,
			enablepowersupply,			
			enableflow1Faultrack1,
			enableflow2Faultrack1,
			enablePumpsLinkrack1,
			enableSecLooprack1,
			enableMainLooprack1,
			enableAuxPowerrack1,
			enableCoolingrack1,
			enablePressureFaultrack1,
			enableCoolingPowerrack1,
			enableExchangeFan1Comrack1,
			enableExchangeFan2Comrack1,
			enablePump1Faultrack1,
			enablePump2Faultrack1,
			enableExchangeFan1Faultrack1,
			enableExchangeFan2Faultrack1,
			enableExchangeLinkrack1,
			enableExchangePowerrack1,
			enablePump1Linkrack1,
			enablePump2Linkrack1,
			enableflow1Faultrack2,
			enableflow2Faultrack2,
			enablePumpsLinkrack2,
			enableSecLooprack2,
			enableMainLooprack2,
			enableAuxPowerrack2,
			enableCoolingrack2,
			enablePressureFaultrack2,
			enableCoolingPowerrack2,
			enableExchangeFan1Comrack2,
			enableExchangeFan2Comrack2,
			enablePump1Faultrack2,
			enablePump2Faultrack2,
			enableExchangeFan1Faultrack2,
			enableExchangeFan2Faultrack2,
			enableExchangeLinkrack2,
			enableExchangePowerrack2,
			enablePump1Linkrack2,
			enablePump2Linkrack2,
			enableinputexcA,
			enablereferenceexcA,
			enableppsexcA,
			enablewarningexcA,
			enablefaultexcA,
			enableoutputPowerexcAFailure,
			enablenoResponseexcA,
			enableantennaLoadexcA,
			enableinputexcB,
			enablereferenceexcB,
			enableppsexcB,
			enablewarningexcB,
			enablefaultexcB,
			enableoutputPowerexcBFailure,
			enablenoResponseexcB,
			enableantennaLoadexcB,
			enableswitchSystemReady,
			enableccuFault,
			enableinterlockFailure,
			enablegpslockA,
			enablesfnreadyA,
			enablevccA,
			enablegpslockB,
			enablesfnreadyB,
			enablevccB,
			enablewarningGPS,
			enablefaultGPS,
			enablenoResponseGPS
      	}
      	STATUS current
      	DESCRIPTION 
        	"Enable Notifications Group"
  	::= { mibGroups 36 }
  	
  groupStateNotifications OBJECT-GROUP
	OBJECTS 
   	{ 			
   		stateinputFailure1, 	
			statereferenceFailure1,
			stateppsFailure1,
			statewarningFailure1,
			statesumfaultFailure1,
			statenoResponseFailure1,
			stateantennaLoadFailure1,
			statepoutFailure1,
			statecoaxialswitchFailure1,
			stateinputFailure2, 	
			statereferenceFailure2,
			stateppsFailure2,
			statewarningFailure2,
			statesumfaultFailure2,
			statenoResponseFailure2,
			stateantennaLoadFailure2,
			statepoutFailure2,
			statecoaxialswitchFailure2,
			stateinputFailure3, 	
			statereferenceFailure3,
			stateppsFailure3,
			statewarningFailure3,
			statesumfaultFailure3,
			statenoResponseFailure3,
			stateantennaLoadFailure3,
			statepoutFailure3,
			statecoaxialswitchFailure3,
			stateinputFailure4, 	
			statereferenceFailure4,
			stateppsFailure4,
			statewarningFailure4,
			statesumfaultFailure4,
			statenoResponseFailure4,
			stateantennaLoadFailure4,
			statepoutFailure4,
			statecoaxialswitchFailure4,
			stateinputFailure5, 	
			statereferenceFailure5,
			stateppsFailure5,
			statewarningFailure5,
			statesumfaultFailure5,
			statenoResponseFailure5,
			stateantennaLoadFailure5,
			statepoutFailure5,
			statecoaxialswitchFailure5,
			stateinputFailure6, 	
			statereferenceFailure6,
			stateppsFailure6,
			statewarningFailure6,
			statesumfaultFailure6,
			statenoResponseFailure6,
			stateantennaLoadFailure6,
			statepoutFailure6,
			statecoaxialswitchFailure6,
			stateinputFailure7, 	
			statereferenceFailure7,
			stateppsFailure7,
			statewarningFailure7,
			statesumfaultFailure7,
			statenoResponseFailure7,
			stateantennaLoadFailure7,
			statepoutFailure7,
			statecoaxialswitchFailure7,
			stateinputFailure8, 	
			statereferenceFailure8,
			stateppsFailure8,
			statewarningFailure8,
			statesumfaultFailure8,
			statenoResponseFailure8,
			stateantennaLoadFailure8,
			statepoutFailure8,
			statecoaxialswitchFailure8,
			stateinputFailureR, 	
			statereferenceFailureR,
			stateppsFailureR,
			statewarningFailureR,
			statesumfaultFailureR,
			statenoResponseFailureR,
			stateantennaLoadFailureR,
			statepoutFailureR,
			statenoResponseMatrix,
			statepoutFailure,
			statereflectedFailure,
			statetemperatureFailure,
			stateturbine1Failure,
			stateturbine2Failure,
			statecoaxialswitchFailure,
			stateamplifierFailure,
			statepowersupplyFailure,
			stateflow1Faultrack1,
			stateflow2Faultrack1,
			statePumpsLinkrack1,
			stateSecLooprack1,
			stateMainLooprack1,
			stateAuxPowerrack1,
			stateCoolingrack1,
			statePressureFaultrack1,
			stateCoolingPowerrack1,
			stateExchangeFan1Comrack1,
			stateExchangeFan2Comrack1,
			statePump1Faultrack1,
			statePump2Faultrack1,
			stateExchangeFan1Faultrack1,
			stateExchangeFan2Faultrack1,
			stateExchangeLinkrack1,
			stateExchangePowerrack1,
			statePump1Linkrack1,
			statePump2Linkrack1,
			stateflow1Faultrack2,
			stateflow2Faultrack2,
			statePumpsLinkrack2,
			stateSecLooprack2,
			stateMainLooprack2,
			stateAuxPowerrack2,
			stateCoolingrack2,
			statePressureFaultrack2,
			stateCoolingPowerrack2,
			stateExchangeFan1Comrack2,
			stateExchangeFan2Comrack2,
			statePump1Faultrack2,
			statePump2Faultrack2,
			stateExchangeFan1Faultrack2,
			stateExchangeFan2Faultrack2,
			stateExchangeLinkrack2,
			stateExchangePowerrack2,
			statePump1Linkrack2,
			statePump2Linkrack2,
			stateinputexcAFailure,
			statereferenceexcAFailure,
			stateppsexcAFailure,
			statewarningexcAFailure,
			statefaultexcAFailure,
			stateoutputPowerexcAFailure,
			statenoResponseexcAFailure,
			stateantennaLoadexcA,
			stateinputexcBFailure,
			statereferenceexcBFailure,
			stateppsexcBFailure,
			statewarningexcBFailure,
			statefaultexcBFailure,
			stateoutputPowerexcBFailure,
			statenoResponseexcBFailure,
			stateantennaLoadexcB,
			stateswitchSystemReady,
			stateccuFault,
			stateinterlockFailure,
			stategpslockAFailure,
			statesfnreadyAFailure,
			statevccAFailure,
			stategpslockBFailure,
			statesfnreadyBFailure,
			statevccBFailure,
			statewarningGPS,
			statefaultGPS,
			statenoResponseGPS
		}
		STATUS current
		DESCRIPTION 
			"Notifications State Group"
	::= { mibGroups 37 }

	groupNotificationData OBJECT-GROUP
	OBJECTS 
		{	
			notificationEdge,
			notificationSeverity
		}
		STATUS current     
		DESCRIPTION
			"Notification Data Group"
	::= {mibGroups 38}

----------------------------------------------------------
    mibModuleCompliance MODULE-COMPLIANCE
      	STATUS current
      	DESCRIPTION 
        	"The compliance statement for entities which implement EGATEL-ccu9000-v18-MIB.MIB"
      	MODULE -- this module
		MANDATORY-GROUPS	
			{ 	
				grouptx1, 
				grouptx2, 
				grouptx3,
				grouptx4,
				grouptx5,
				grouptx6,
				grouptx7,
				grouptx8,
				grouptxR,
				groupmatrix,
				groupconfignplusone,
				grouppower,
				groupamplifier1,
        			groupamplifier2,
        			groupamplifier3,
        			groupamplifier4,
        			groupamplifier5,
       			groupamplifier6,
        			groupamplifier7,
        			groupamplifier8,
        			groupamplifier9,
        			groupamplifier10,
        			groupamplifier11,
        			groupamplifier12,
        			groupamplifier13,
       			groupamplifier14,
        			groupamplifier15,
        			groupamplifier16,
				grouprack,
				groupexcA,
				groupexcB,
				groupconfigSDDD,
				groupccu,
				groupgps,
				groupNotifications,
				groupStateNotifications,
				groupEnableNotifications,
				groupNotificationData 
      }
   ::= { mibCompliance 1 }

--------------------------------------------------------------
    mibAgentCapabilities AGENT-CAPABILITIES
	PRODUCT-RELEASE 
	"Agent CCU9000 SNMP v18 Egatel 2016"
	STATUS current
	DESCRIPTION 
	"Egatel, S.L. Agent for ccu9000"
	SUPPORTS SNMPv2-MIB
	INCLUDES	{ systemGroup }  
	SUPPORTS EGATEL-ccu9000-v18-MIB
	INCLUDES	
		{ 	
			grouptx1, 
			grouptx2, 
			grouptx3,
			grouptx4,
			grouptx5,
			grouptx6,
			grouptx7,
			grouptx8,
			grouptxR,
			groupmatrix,
			groupconfignplusone,
			grouppower,
			groupamplifier1,
			groupamplifier2,
			groupamplifier3,
			groupamplifier4,
			groupamplifier5,
			groupamplifier6,
			groupamplifier7,
			groupamplifier8,
			groupamplifier9,
			groupamplifier10,
			groupamplifier11,
			groupamplifier12,
			groupamplifier13,
			groupamplifier14,
			groupamplifier15,
			groupamplifier16,
			grouprack,
			groupexcA,
			groupexcB,
			groupconfigSDDD,
			groupccu,
			groupgps,
			groupNotifications,
			groupEnableNotifications,
			groupNotificationData 
		}      			
	::= { mibCapabilities 1 }

----------------------------------------------------------
----------------------------------------------------------
	notificationEdge OBJECT-TYPE
		SYNTAX INTEGER {active(1), inactive(2)}  
		MAX-ACCESS accessible-for-notify
		STATUS	current
		DESCRIPTION
			"Failure active/inactive changed:
				active (1)   --> failure is on
				inactive (2) --> failure is off"
	::= {notificationNode 13}

	notificationSeverity OBJECT-TYPE
		SYNTAX INTEGER {	fault(3), warning(4), state(5) }
		MAX-ACCESS accessible-for-notify
		STATUS	current
		DESCRIPTION                     
			"Severity of the notification"
	::= {notificationNode 14}
	
---------------------------------------------------------------------------
---------------------------------------------------------------------------    
	inputFailure1 NOTIFICATION-TYPE    
		OBJECTS {notificationEdge,notificationSeverity, stateinputFailure1}
		STATUS current
		DESCRIPTION
			"No input on Transmitter 1"
	::= {notificationtx1 1}        
	
	referenceFailure1 NOTIFICATION-TYPE    
		OBJECTS {notificationEdge,notificationSeverity, statereferenceFailure1}
		STATUS current
		DESCRIPTION
			"Transmitter 1 External 10MHz fault"
	::= {notificationtx1 2} 
	
	ppsFailure1 NOTIFICATION-TYPE    
		OBJECTS {notificationEdge, notificationSeverity, stateppsFailure1}
		STATUS current
		DESCRIPTION
			"Transmitter 1 PPS fault"
	::= {notificationtx1 3}                                          	                                               
	                                     
	warningFailure1 NOTIFICATION-TYPE    
		OBJECTS {notificationEdge, notificationSeverity, statewarningFailure1}
		STATUS current
		DESCRIPTION
			"Transmitter 1 WARNING"
	::= {notificationtx1 4}                                          	                                               	                                     
	
	sumfaultFailure1 NOTIFICATION-TYPE    
		OBJECTS {notificationEdge, notificationSeverity, statesumfaultFailure1}
		STATUS current
		DESCRIPTION
			"Transmitter 1 SUMFAULT"
	::= {notificationtx1 5}
	
	noResponseFailure1 NOTIFICATION-TYPE    
		OBJECTS {notificationEdge, notificationSeverity, statenoResponseFailure1}
		STATUS current
		DESCRIPTION
			"No response from Transmitter 1"
	::= {notificationtx1 6}
	
	antennaLoadFailure1 NOTIFICATION-TYPE    
		OBJECTS {notificationEdge, notificationSeverity, stateantennaLoadFailure1}
		STATUS current
		DESCRIPTION
			"Transmitter 1 Antenna or Load"
	::= {notificationtx1 7}
	
	poutFailure1 NOTIFICATION-TYPE    
		OBJECTS {notificationEdge, notificationSeverity, statepoutFailure1}
		STATUS current
		DESCRIPTION
			"Transmitter 1 low Pout"
	::= {notificationtx1 8}
	
	coaxialswitchFailure1 NOTIFICATION-TYPE    
		OBJECTS {notificationEdge, notificationSeverity, statecoaxialswitchFailure1}
		STATUS current
		DESCRIPTION
			"Coaxial Relay 1 failure"
	::= {notificationtx1 9}
	
	inputFailure2 NOTIFICATION-TYPE    
		OBJECTS {notificationEdge, notificationSeverity, stateinputFailure2}
		STATUS current
		DESCRIPTION
			"No input on Transmitter 2"
	::= {notificationtx2 1}        
	
	referenceFailure2 NOTIFICATION-TYPE    
		OBJECTS {notificationEdge, notificationSeverity, statereferenceFailure2}
		STATUS current
		DESCRIPTION
			"Transmitter 2 External 10MHz fault"
	::= {notificationtx2 2} 
	
	ppsFailure2 NOTIFICATION-TYPE    
		OBJECTS {notificationEdge, notificationSeverity, stateppsFailure2}
		STATUS current
		DESCRIPTION
			"Transmitter 2 PPS fault"
	::= {notificationtx2 3}                                          	                                               
	                                     
	warningFailure2 NOTIFICATION-TYPE    
		OBJECTS {notificationEdge, notificationSeverity, statewarningFailure2}
		STATUS current
		DESCRIPTION
			"Transmitter 2 WARNING"
	::= {notificationtx2 4}
	
	sumfaultFailure2 NOTIFICATION-TYPE    
		OBJECTS {notificationEdge, notificationSeverity, statesumfaultFailure2}
		STATUS current
		DESCRIPTION
			"Transmitter 2 SUMFAULT"
	::= {notificationtx2 5}
	
	noResponseFailure2 NOTIFICATION-TYPE    
		OBJECTS {notificationEdge, notificationSeverity, statenoResponseFailure2}
		STATUS current
		DESCRIPTION
			"No response from Transmitter 2"
	::= {notificationtx2 6}
	
	antennaLoadFailure2 NOTIFICATION-TYPE    
		OBJECTS {notificationEdge, notificationSeverity, stateantennaLoadFailure2}
		STATUS current
		DESCRIPTION
			"Transmitter 2 Antenna or Load"
	::= {notificationtx2 7}
	
	poutFailure2 NOTIFICATION-TYPE    
		OBJECTS {notificationEdge, notificationSeverity, statepoutFailure2}
		STATUS current
		DESCRIPTION
			"Transmitter 2 low Pout"
	::= {notificationtx2 8}
	
	coaxialswitchFailure2 NOTIFICATION-TYPE    
		OBJECTS {notificationEdge, notificationSeverity, statecoaxialswitchFailure2}
		STATUS current
		DESCRIPTION
			"Coaxial Relay 2 failure"
	::= {notificationtx2 9}

	inputFailure3 NOTIFICATION-TYPE    
		OBJECTS {notificationEdge, notificationSeverity, stateinputFailure3}
		STATUS current
		DESCRIPTION
			"No input on Transmitter 3"
	::= {notificationtx3 1}        
	
	referenceFailure3 NOTIFICATION-TYPE    
		OBJECTS {notificationEdge, notificationSeverity, statereferenceFailure3}
		STATUS current
		DESCRIPTION
			"Transmitter 3 External 10MHz fault"
	::= {notificationtx3 2} 
	
	ppsFailure3 NOTIFICATION-TYPE    
		OBJECTS {notificationEdge, notificationSeverity, stateppsFailure3}
		STATUS current
		DESCRIPTION
			"Transmitter 3 PPS fault"
	::= {notificationtx3 3}

	warningFailure3 NOTIFICATION-TYPE
		OBJECTS {notificationEdge, notificationSeverity, statewarningFailure3}
		STATUS current
		DESCRIPTION
			"Transmitter 3 WARNING"
	::= {notificationtx3 4}
	
	sumfaultFailure3 NOTIFICATION-TYPE
		OBJECTS {notificationEdge, notificationSeverity, statesumfaultFailure3}
		STATUS current
		DESCRIPTION
			"Transmitter 3 SUMFAULT"
	::= {notificationtx3 5}
	
	noResponseFailure3 NOTIFICATION-TYPE    
		OBJECTS {notificationEdge, notificationSeverity, statenoResponseFailure3}
		STATUS current
		DESCRIPTION
			"No response from Transmitter 3"
	::= {notificationtx3 6}
	
	antennaLoadFailure3 NOTIFICATION-TYPE    
		OBJECTS {notificationEdge, notificationSeverity, stateantennaLoadFailure3}
		STATUS current
		DESCRIPTION
			"Transmitter 3 Antenna or Load"
	::= {notificationtx3 7}
	
	poutFailure3 NOTIFICATION-TYPE    
		OBJECTS {notificationEdge, notificationSeverity, statepoutFailure3}
		STATUS current
		DESCRIPTION
			"Transmitter 3 low Pout"
	::= {notificationtx3 8}
	
	coaxialswitchFailure3 NOTIFICATION-TYPE    
		OBJECTS {notificationEdge, notificationSeverity, statecoaxialswitchFailure3}
		STATUS current
		DESCRIPTION
			"Coaxial Relay 3 failure"
	::= {notificationtx3 9}

	inputFailure4 NOTIFICATION-TYPE    
		OBJECTS {notificationEdge, notificationSeverity, stateinputFailure4}
		STATUS current
		DESCRIPTION
			"No input on Transmitter 4"
	::= {notificationtx4 1}        
	
	referenceFailure4 NOTIFICATION-TYPE    
		OBJECTS {notificationEdge, notificationSeverity, statereferenceFailure4}
		STATUS current
		DESCRIPTION
			"Transmitter 4 External 10MHz fault"
	::= {notificationtx4 2} 
	
	ppsFailure4 NOTIFICATION-TYPE    
		OBJECTS {notificationEdge, notificationSeverity, stateppsFailure4}
		STATUS current
		DESCRIPTION
			"Transmitter 4 PPS fault"
	::= {notificationtx4 3}                                          	                                               
	                                     
	warningFailure4 NOTIFICATION-TYPE    
		OBJECTS {notificationEdge, notificationSeverity, statewarningFailure4}
		STATUS current
		DESCRIPTION
			"Transmitter 4 WARNING"
	::= {notificationtx4 4}                                          	                                               	                                     
	
	sumfaultFailure4 NOTIFICATION-TYPE    
		OBJECTS {notificationEdge, notificationSeverity, statesumfaultFailure4}
		STATUS current
		DESCRIPTION
			"Transmitter 4 SUMFAULT"
	::= {notificationtx4 5}
	
	noResponseFailure4 NOTIFICATION-TYPE    
		OBJECTS {notificationEdge, notificationSeverity, statenoResponseFailure4}
		STATUS current
		DESCRIPTION
			"No response from Transmitter 4"
	::= {notificationtx4 6}
	
	antennaLoadFailure4 NOTIFICATION-TYPE    
		OBJECTS {notificationEdge, notificationSeverity, stateantennaLoadFailure4}
		STATUS current
		DESCRIPTION
			"Transmitter 4 Antenna or Load"
	::= {notificationtx4 7}
	
	poutFailure4 NOTIFICATION-TYPE    
		OBJECTS {notificationEdge, notificationSeverity, statepoutFailure4}
		STATUS current
		DESCRIPTION
			"Transmitter 4 low Pout"
	::= {notificationtx4 8}
	
	coaxialswitchFailure4 NOTIFICATION-TYPE    
		OBJECTS {notificationEdge, notificationSeverity, statecoaxialswitchFailure4}
		STATUS current
		DESCRIPTION
			"Coaxial Relay 4 failure"
	::= {notificationtx4 9}

	inputFailure5 NOTIFICATION-TYPE    
		OBJECTS {notificationEdge, notificationSeverity, stateinputFailure5}
		STATUS current
		DESCRIPTION
			"No input on Transmitter 5"
	::= {notificationtx5 1}        
	
	referenceFailure5 NOTIFICATION-TYPE    
		OBJECTS {notificationEdge, notificationSeverity, statereferenceFailure5}
		STATUS current
		DESCRIPTION
			"Transmitter 5 External 10MHz fault"
	::= {notificationtx5 2} 
	
	ppsFailure5 NOTIFICATION-TYPE    
		OBJECTS {notificationEdge, notificationSeverity, stateppsFailure5}
		STATUS current
		DESCRIPTION
			"Transmitter 5 PPS fault"
	::= {notificationtx5 3}                                          	                                               
	                                     
	warningFailure5 NOTIFICATION-TYPE    
		OBJECTS {notificationEdge, notificationSeverity, statewarningFailure5}
		STATUS current
		DESCRIPTION
			"Transmitter 5 WARNING"
	::= {notificationtx5 4}                                          	                                               	                                     
	
	sumfaultFailure5 NOTIFICATION-TYPE    
		OBJECTS {notificationEdge, notificationSeverity, statesumfaultFailure5}
		STATUS current
		DESCRIPTION
			"Transmitter 5 SUMFAULT"
	::= {notificationtx5 5}
	
	noResponseFailure5 NOTIFICATION-TYPE    
		OBJECTS {notificationEdge, notificationSeverity, statenoResponseFailure5}
		STATUS current
		DESCRIPTION
			"No response from Transmitter 5"
	::= {notificationtx5 6}
	
	antennaLoadFailure5 NOTIFICATION-TYPE    
		OBJECTS {notificationEdge, notificationSeverity, stateantennaLoadFailure5}
		STATUS current
		DESCRIPTION
			"Transmitter 5 Antenna or Load"
	::= {notificationtx5 7}
	
	poutFailure5 NOTIFICATION-TYPE    
		OBJECTS {notificationEdge, notificationSeverity, statepoutFailure5}
		STATUS current
		DESCRIPTION
			"Transmitter 5 low Pout"
	::= {notificationtx5 8}
	
	coaxialswitchFailure5 NOTIFICATION-TYPE    
		OBJECTS {notificationEdge, notificationSeverity, statecoaxialswitchFailure5}
		STATUS current
		DESCRIPTION
			"Coaxial Relay 5 failure"
	::= {notificationtx5 9}

	inputFailure6 NOTIFICATION-TYPE    
		OBJECTS {notificationEdge, notificationSeverity, stateinputFailure6}
		STATUS current
		DESCRIPTION
			"No input on Transmitter 6"
	::= {notificationtx6 1}        
	
	referenceFailure6 NOTIFICATION-TYPE    
		OBJECTS {notificationEdge, notificationSeverity, statereferenceFailure6}
		STATUS current
		DESCRIPTION
			"Transmitter 6 External 10MHz fault"
	::= {notificationtx6 2} 
	
	ppsFailure6 NOTIFICATION-TYPE    
		OBJECTS {notificationEdge, notificationSeverity, stateppsFailure6}
		STATUS current
		DESCRIPTION
			"Transmitter 6 PPS fault"
	::= {notificationtx6 3}                                          	                                               
	                                     
	warningFailure6 NOTIFICATION-TYPE    
		OBJECTS {notificationEdge, notificationSeverity, statewarningFailure6}
		STATUS current
		DESCRIPTION
			"Transmitter 6 WARNING"
	::= {notificationtx6 4}                                          	                                               	                                     
	
	sumfaultFailure6 NOTIFICATION-TYPE    
		OBJECTS {notificationEdge, notificationSeverity, statesumfaultFailure6}
		STATUS current
		DESCRIPTION
			"Transmitter 6 SUMFAULT"
	::= {notificationtx6 5}
	
	noResponseFailure6 NOTIFICATION-TYPE    
		OBJECTS {notificationEdge, notificationSeverity, statenoResponseFailure6}
		STATUS current
		DESCRIPTION
			"No response from Transmitter 6"
	::= {notificationtx6 6}
	
	antennaLoadFailure6 NOTIFICATION-TYPE    
		OBJECTS {notificationEdge, notificationSeverity, stateantennaLoadFailure6}
		STATUS current
		DESCRIPTION
			"Transmitter 6 Antenna or Load"
	::= {notificationtx6 7}
	
	poutFailure6 NOTIFICATION-TYPE    
		OBJECTS {notificationEdge, notificationSeverity, statepoutFailure6}
		STATUS current
		DESCRIPTION
			"Transmitter 6 low Pout"
	::= {notificationtx6 8}
	
	coaxialswitchFailure6 NOTIFICATION-TYPE    
		OBJECTS {notificationEdge, notificationSeverity, statecoaxialswitchFailure6}
		STATUS current
		DESCRIPTION
			"Coaxial Relay 6 failure"
	::= {notificationtx6 9}

	inputFailure7 NOTIFICATION-TYPE    
		OBJECTS {notificationEdge, notificationSeverity, stateinputFailure7}
		STATUS current
		DESCRIPTION
			"No input on Transmitter 7"
	::= {notificationtx7 1}        
	
	referenceFailure7 NOTIFICATION-TYPE    
		OBJECTS {notificationEdge, notificationSeverity, statereferenceFailure7}
		STATUS current
		DESCRIPTION
			"Transmitter 7 External 10MHz fault"
	::= {notificationtx7 2} 
	
	ppsFailure7 NOTIFICATION-TYPE    
		OBJECTS {notificationEdge, notificationSeverity, stateppsFailure7}
		STATUS current
		DESCRIPTION
			"Transmitter 7 PPS fault"
	::= {notificationtx7 3}                                          	                                               
	                                     
	warningFailure7 NOTIFICATION-TYPE    
		OBJECTS {notificationEdge, notificationSeverity, statewarningFailure7}
		STATUS current
		DESCRIPTION
			"Transmitter 7 WARNING"
	::= {notificationtx7 4}                                          	                                               	                                     
	
	sumfaultFailure7 NOTIFICATION-TYPE    
		OBJECTS {notificationEdge, notificationSeverity, statesumfaultFailure7}
		STATUS current
		DESCRIPTION
			"Transmitter 7 SUMFAULT"
	::= {notificationtx7 5}
	
	noResponseFailure7 NOTIFICATION-TYPE    
		OBJECTS {notificationEdge, notificationSeverity, statenoResponseFailure7}
		STATUS current
		DESCRIPTION
			"No response from Transmitter 7"
	::= {notificationtx7 6}
	
	antennaLoadFailure7 NOTIFICATION-TYPE    
		OBJECTS {notificationEdge, notificationSeverity, stateantennaLoadFailure7}
		STATUS current
		DESCRIPTION
			"Transmitter 7 Antenna or Load"
	::= {notificationtx7 7}
	
	poutFailure7 NOTIFICATION-TYPE    
		OBJECTS {notificationEdge, notificationSeverity, statepoutFailure7}
		STATUS current
		DESCRIPTION
			"Transmitter 7 low Pout"
	::= {notificationtx7 8}
	
	coaxialswitchFailure7 NOTIFICATION-TYPE    
		OBJECTS {notificationEdge, notificationSeverity, statecoaxialswitchFailure7}
		STATUS current
		DESCRIPTION
			"Coaxial Relay 7 failure"
	::= {notificationtx7 9}

	inputFailure8 NOTIFICATION-TYPE    
		OBJECTS {notificationEdge, notificationSeverity, stateinputFailure8}
		STATUS current
		DESCRIPTION
			"No input on Transmitter 8"
	::= {notificationtx8 1}        
	
	referenceFailure8 NOTIFICATION-TYPE    
		OBJECTS {notificationEdge, notificationSeverity, statereferenceFailure8}
		STATUS current
		DESCRIPTION
			"Transmitter 8 External 10MHz fault"
	::= {notificationtx8 2} 
	
	ppsFailure8 NOTIFICATION-TYPE    
		OBJECTS {notificationEdge, notificationSeverity, stateppsFailure8}
		STATUS current
		DESCRIPTION
			"Transmitter 8 PPS fault"
	::= {notificationtx8 3}

	warningFailure8 NOTIFICATION-TYPE    
		OBJECTS {notificationEdge, notificationSeverity, statewarningFailure8}
		STATUS current
		DESCRIPTION
			"Transmitter 8 WARNING"
	::= {notificationtx8 4}
	
	sumfaultFailure8 NOTIFICATION-TYPE    
		OBJECTS {notificationEdge, notificationSeverity, statesumfaultFailure8}
		STATUS current
		DESCRIPTION
			"Transmitter 8 SUMFAULT"
	::= {notificationtx8 5}
	
	noResponseFailure8 NOTIFICATION-TYPE    
		OBJECTS {notificationEdge, notificationSeverity, statenoResponseFailure8}
		STATUS current
		DESCRIPTION
			"No response from Transmitter 8"
	::= {notificationtx8 6}
	
	antennaLoadFailure8 NOTIFICATION-TYPE    
		OBJECTS {notificationEdge, notificationSeverity, stateantennaLoadFailure8}
		STATUS current
		DESCRIPTION
			"Transmitter 8 Antenna or Load"
	::= {notificationtx8 7}
	
	poutFailure8 NOTIFICATION-TYPE    
		OBJECTS {notificationEdge, notificationSeverity, statepoutFailure8}
		STATUS current
		DESCRIPTION
			"Transmitter 8 low Pout"
	::= {notificationtx8 8}
	
	coaxialswitchFailure8 NOTIFICATION-TYPE    
		OBJECTS {notificationEdge, notificationSeverity, statecoaxialswitchFailure8}
		STATUS current
		DESCRIPTION
			"Coaxial Relay 8 failure"
	::= {notificationtx8 9}

	inputFailureR NOTIFICATION-TYPE    
		OBJECTS {notificationEdge, notificationSeverity, stateinputFailureR}
		STATUS current
		DESCRIPTION
			"No input on Reserve Transmitter"
	::= {notificationtxR 1}        
	
	referenceFailureR NOTIFICATION-TYPE    
		OBJECTS {notificationEdge, notificationSeverity, statereferenceFailureR}
		STATUS current
		DESCRIPTION
			"Reserve Transmitter External 10MHz fault"
	::= {notificationtxR 2} 
	
	ppsFailureR NOTIFICATION-TYPE    
		OBJECTS {notificationEdge, notificationSeverity, stateppsFailureR}
		STATUS current
		DESCRIPTION
			"Reserve Transmitter PPS fault"
	::= {notificationtxR 3}                                          	                                               
	                                     
	warningFailureR NOTIFICATION-TYPE    
		OBJECTS {notificationEdge, notificationSeverity, statewarningFailureR}
		STATUS current
		DESCRIPTION
			"Reserve Transmitter WARNING"
	::= {notificationtxR 4}                                          	                                               	                                     
	
	sumfaultFailureR NOTIFICATION-TYPE    
		OBJECTS {notificationEdge, notificationSeverity, statesumfaultFailureR}
		STATUS current
		DESCRIPTION
			"Reserve Transmitter SUMFAULT"
	::= {notificationtxR 5}
	
	noResponseFailureR NOTIFICATION-TYPE    
		OBJECTS {notificationEdge, notificationSeverity, statenoResponseFailureR}
		STATUS current
		DESCRIPTION
			"No response from Reserve Transmitter"
	::= {notificationtxR 6}
	
	antennaLoadFailureR NOTIFICATION-TYPE    
		OBJECTS {notificationEdge, notificationSeverity, stateantennaLoadFailureR}
		STATUS current
		DESCRIPTION
			"Reserve Transmitter Antenna or Load"
	::= {notificationtxR 7}
	
	poutFailureR NOTIFICATION-TYPE    
		OBJECTS {notificationEdge, notificationSeverity, statepoutFailureR}
		STATUS current
		DESCRIPTION
			"Reserve Transmitter low Pout"
	::= {notificationtxR 8}
	
--------------------------------------------------------------------------------------------------------
	
	noResponseMatrix NOTIFICATION-TYPE    
		OBJECTS {notificationEdge, notificationSeverity, statenoResponseMatrix}
		STATUS current
		DESCRIPTION
			"No response from ASI Matrix"
	::= {notificationMatrix 1}

--------------------------------------------------------------------------------------------------------

	poutFailure NOTIFICATION-TYPE    
		OBJECTS {notificationEdge, notificationSeverity, statepoutFailure}
		STATUS current
		DESCRIPTION
			"Low Pout"
	::= {notificationpower 1}
	
	reflectedFailure NOTIFICATION-TYPE    
		OBJECTS {notificationEdge, notificationSeverity, statereflectedFailure}
		STATUS current
		DESCRIPTION
			"High reflected Power"
	::= {notificationpower 2}

	temperatureFailure NOTIFICATION-TYPE    
		OBJECTS {notificationEdge, notificationSeverity, statetemperatureFailure}
		STATUS current
		DESCRIPTION
			"High temperature"
	::= {notificationrack 1}

	turbine1 NOTIFICATION-TYPE    
		OBJECTS {notificationEdge, notificationSeverity, stateturbine1Failure}
		STATUS current
		DESCRIPTION
			"Turbine 1 failure"
	::= {notificationrack 2}
	
	turbine2 NOTIFICATION-TYPE    
		OBJECTS {notificationEdge, notificationSeverity, stateturbine2Failure}
		STATUS current
		DESCRIPTION
			"Turbine 2 failure"
	::= {notificationrack 3}
	
	coaxialswitch NOTIFICATION-TYPE    
		OBJECTS {notificationEdge, notificationSeverity, statecoaxialswitchFailure}
		STATUS current
		DESCRIPTION
			"Coaxial switch failure"
	::= {notificationrack 4}
	
	amplifier NOTIFICATION-TYPE    
		OBJECTS {notificationEdge, notificationSeverity, stateamplifierFailure}
		STATUS current
		DESCRIPTION
			"Amplifier failure"
	::= {notificationrack 5}
	
	powersupply NOTIFICATION-TYPE    
		OBJECTS {notificationEdge, notificationSeverity, statepowersupplyFailure}
		STATUS current
		DESCRIPTION
			"Power supply failure"
	::= {notificationrack 6}

	flow1Faultrack1 NOTIFICATION-TYPE    
		OBJECTS {notificationEdge, notificationSeverity, stateflow1Faultrack1}
		STATUS current
		DESCRIPTION
			"flow detect 1 failure"
	::= {notificationrack 7}
	
	flow2Faultrack1 NOTIFICATION-TYPE    
		OBJECTS {notificationEdge, notificationSeverity, stateflow2Faultrack1}
		STATUS current
		DESCRIPTION
			"flow detect 2 failure"
	::= {notificationrack 8}
	
	pumpsLinkrack1 NOTIFICATION-TYPE    
		OBJECTS {notificationEdge, notificationSeverity, statePumpsLinkrack1}
		STATUS current
		DESCRIPTION
			"Pumps link failure"
	::= {notificationrack 9}
	
	secLooprack1 NOTIFICATION-TYPE    
		OBJECTS {notificationEdge, notificationSeverity, stateSecLooprack1}
		STATUS current
		DESCRIPTION
			"Secondary loop failure"
	::= {notificationrack 10}
	
	mainLooprack1 NOTIFICATION-TYPE    
		OBJECTS {notificationEdge, notificationSeverity, stateMainLooprack1}
		STATUS current
		DESCRIPTION
			"Main loop failure"
	::= {notificationrack 11}
	
	auxPowerrack1 NOTIFICATION-TYPE    
		OBJECTS {notificationEdge, notificationSeverity, stateAuxPowerrack1}
		STATUS current
		DESCRIPTION
			"Control Rack Power supply failure"
	::= {notificationrack 12}
	
	coolingrack1 NOTIFICATION-TYPE    
		OBJECTS {notificationEdge, notificationSeverity, stateCoolingrack1}
		STATUS current
		DESCRIPTION
			"Cooling system general failure"
	::= {notificationrack 13}
	
	pressureFaultrack1 NOTIFICATION-TYPE    
		OBJECTS {notificationEdge, notificationSeverity, statePressureFaultrack1}
		STATUS current
		DESCRIPTION
			"Pressure failure"
	::= {notificationrack 14}
	
	coolingPowerrack1 NOTIFICATION-TYPE    
		OBJECTS {notificationEdge, notificationSeverity, stateCoolingPowerrack1}
		STATUS current
		DESCRIPTION
			"Cooling power supply failure"
	::= {notificationrack 15}
	
	exchangeFan1Comrack1 NOTIFICATION-TYPE    
		OBJECTS {notificationEdge, notificationSeverity, stateExchangeFan1Comrack1}
		STATUS current
		DESCRIPTION
			"Heat Exchange Fan 1 communications failure"
	::= {notificationrack 16}
	
	exchangeFan2Comrack1 NOTIFICATION-TYPE    
		OBJECTS {notificationEdge, notificationSeverity, stateExchangeFan2Comrack1}
		STATUS current
		DESCRIPTION
			"Heat Exchange Fan 2 communications failure"
	::= {notificationrack 17}
	
	pump1Faultrack1 NOTIFICATION-TYPE    
		OBJECTS {notificationEdge, notificationSeverity, statePump1Faultrack1}
		STATUS current
		DESCRIPTION
			"Pump 1 failure"
	::= {notificationrack 18}
	
	pump2Faultrack1 NOTIFICATION-TYPE    
		OBJECTS {notificationEdge, notificationSeverity, statePump2Faultrack1}
		STATUS current
		DESCRIPTION
			"Pump 2 failure"
	::= {notificationrack 19}
	
	exchangeFan1Faultrack1 NOTIFICATION-TYPE    
		OBJECTS {notificationEdge, notificationSeverity, stateExchangeFan1Faultrack1}
		STATUS current
		DESCRIPTION
			"Exchange Fan 1 failure"
	::= {notificationrack 20}
	
	exchangeFan2Faultrack1 NOTIFICATION-TYPE    
		OBJECTS {notificationEdge, notificationSeverity, stateExchangeFan2Faultrack1}
		STATUS current
		DESCRIPTION
			"Exchange Fan 2 failure"
	::= {notificationrack 21}
	
	exchangeLinkrack1 NOTIFICATION-TYPE    
		OBJECTS {notificationEdge, notificationSeverity, stateExchangeLinkrack1}
		STATUS current
		DESCRIPTION
			"Heat Exchange link failure"
	::= {notificationrack 22}
	
	exchangePowerrack1 NOTIFICATION-TYPE    
		OBJECTS {notificationEdge, notificationSeverity, stateExchangePowerrack1}
		STATUS current
		DESCRIPTION
			"Heat Exchange power supply failure"
	::= {notificationrack 23}
	
	pump1Linkrack1 NOTIFICATION-TYPE    
		OBJECTS {notificationEdge, notificationSeverity, statePump1Linkrack1}
		STATUS current
		DESCRIPTION
			"Pump 1 link failure"
	::= {notificationrack 24}
	
	pump2Linkrack1 NOTIFICATION-TYPE    
		OBJECTS {notificationEdge, notificationSeverity, statePump2Linkrack1}
		STATUS current
		DESCRIPTION
			"Pump 2 link failure"
	::= {notificationrack 25}
	
	flow1Faultrack2 NOTIFICATION-TYPE    
		OBJECTS {notificationEdge, notificationSeverity, stateflow1Faultrack2}
		STATUS current
		DESCRIPTION
			"flow detect 1 failure"
	::= {notificationrack 26}
	
	flow2Faultrack2 NOTIFICATION-TYPE    
		OBJECTS {notificationEdge, notificationSeverity, stateflow2Faultrack2}
		STATUS current
		DESCRIPTION
			"flow detect 2 failure"
	::= {notificationrack 27}
	
	pumpsLinkrack2 NOTIFICATION-TYPE    
		OBJECTS {notificationEdge, notificationSeverity, statePumpsLinkrack2}
		STATUS current
		DESCRIPTION
			"Pumps link failure"
	::= {notificationrack 28}
	
	secLooprack2 NOTIFICATION-TYPE    
		OBJECTS {notificationEdge, notificationSeverity, stateSecLooprack2}
		STATUS current
		DESCRIPTION
			"Secondary loop failure"
	::= {notificationrack 29}
	
	mainLooprack2 NOTIFICATION-TYPE    
		OBJECTS {notificationEdge, notificationSeverity, stateMainLooprack2}
		STATUS current
		DESCRIPTION
			"Main loop failure"
	::= {notificationrack 30}
	
	auxPowerrack2 NOTIFICATION-TYPE    
		OBJECTS {notificationEdge, notificationSeverity, stateAuxPowerrack2}
		STATUS current
		DESCRIPTION
			"Control Rack Power supply failure"
	::= {notificationrack 31}
	
	coolingrack2 NOTIFICATION-TYPE    
		OBJECTS {notificationEdge, notificationSeverity, stateCoolingrack2}
		STATUS current
		DESCRIPTION
			"Cooling system general failure"
	::= {notificationrack 32}
	
	pressureFaultrack2 NOTIFICATION-TYPE    
		OBJECTS {notificationEdge, notificationSeverity, statePressureFaultrack2}
		STATUS current
		DESCRIPTION
			"Pressure failure"
	::= {notificationrack 33}
	
	coolingPowerrack2 NOTIFICATION-TYPE    
		OBJECTS {notificationEdge, notificationSeverity, stateCoolingPowerrack2}
		STATUS current
		DESCRIPTION
			"Cooling power supply failure"
	::= {notificationrack 34}
	
	exchangeFan1Comrack2 NOTIFICATION-TYPE    
		OBJECTS {notificationEdge, notificationSeverity, stateExchangeFan1Comrack2}
		STATUS current
		DESCRIPTION
			"Heat Exchange Fan 1 communications failure"
	::= {notificationrack 35}
	
	exchangeFan2Comrack2 NOTIFICATION-TYPE    
		OBJECTS {notificationEdge, notificationSeverity, stateExchangeFan2Comrack2}
		STATUS current
		DESCRIPTION
			"Heat Exchange Fan 2 communications failure"
	::= {notificationrack 36}
	
	pump1Faultrack2 NOTIFICATION-TYPE    
		OBJECTS {notificationEdge, notificationSeverity, statePump1Faultrack2}
		STATUS current
		DESCRIPTION
			"Pump 1 failure"
	::= {notificationrack 37}
	
	pump2Faultrack2 NOTIFICATION-TYPE    
		OBJECTS {notificationEdge, notificationSeverity, statePump2Faultrack2}
		STATUS current
		DESCRIPTION
			"Pump 2 failure"
	::= {notificationrack 38}
	
	exchangeFan1Faultrack2 NOTIFICATION-TYPE    
		OBJECTS {notificationEdge, notificationSeverity, stateExchangeFan1Faultrack2}
		STATUS current
		DESCRIPTION
			"Exchange Fan 1 failure"
	::= {notificationrack 39}
	
	exchangeFan2Faultrack2 NOTIFICATION-TYPE    
		OBJECTS {notificationEdge, notificationSeverity, stateExchangeFan2Faultrack2}
		STATUS current
		DESCRIPTION
			"Exchange Fan 2 failure"
	::= {notificationrack 40}
	
	exchangeLinkrack2 NOTIFICATION-TYPE    
		OBJECTS {notificationEdge, notificationSeverity, stateExchangeLinkrack2}
		STATUS current
		DESCRIPTION
			"Heat Exchange link failure"
	::= {notificationrack 41}
	
	exchangePowerrack2 NOTIFICATION-TYPE    
		OBJECTS {notificationEdge, notificationSeverity, stateExchangePowerrack2}
		STATUS current
		DESCRIPTION
			"Heat Exchange power supply failure"
	::= {notificationrack 42}
	
	pump1Linkrack2 NOTIFICATION-TYPE    
		OBJECTS {notificationEdge, notificationSeverity, statePump1Linkrack2}
		STATUS current
		DESCRIPTION
			"Pump 1 link failure"
	::= {notificationrack 43}
	
	pump2Linkrack2 NOTIFICATION-TYPE    
		OBJECTS {notificationEdge, notificationSeverity, statePump2Linkrack2}
		STATUS current
		DESCRIPTION
			"Pump 2 link failure"
	::= {notificationrack 44}
--------------------------------------------------------------------------------------------------------

	inputexcA NOTIFICATION-TYPE    
		OBJECTS {notificationEdge, notificationSeverity, stateinputexcAFailure}
		STATUS current
		DESCRIPTION
			"No input on exciter A"
	::= {notificationexcA 1}
	
	referenceexcA NOTIFICATION-TYPE    
		OBJECTS {notificationEdge, notificationSeverity, statereferenceexcAFailure}
		STATUS current
		DESCRIPTION
			"Exciter A external 10MHz fault"
	::= {notificationexcA 2}
	
	ppsexcA NOTIFICATION-TYPE    
		OBJECTS {notificationEdge, notificationSeverity, stateppsexcAFailure}
		STATUS current
		DESCRIPTION
			"Exciter A pps fault"
	::= {notificationexcA 3}
	
	warningexcA NOTIFICATION-TYPE    
		OBJECTS {notificationEdge, notificationSeverity, statewarningexcAFailure}
		STATUS current
		DESCRIPTION
			"Exciter A WARNING"
	::= {notificationexcA 4}                                          	                                               	                                     
	
	faultexcA NOTIFICATION-TYPE    
		OBJECTS {notificationEdge, notificationSeverity, statefaultexcAFailure}
		STATUS current
		DESCRIPTION
			"Exciter A FAULT"
	::= {notificationexcA 5}
	
	outputPowerexcAFailure NOTIFICATION-TYPE    
		OBJECTS {notificationEdge, notificationSeverity, stateoutputPowerexcAFailure}
		STATUS current
		DESCRIPTION
			"Exciter A output power FAULT"
	::= {notificationexcA 6}
	
	noResponseexcA NOTIFICATION-TYPE    
		OBJECTS {notificationEdge, notificationSeverity, statenoResponseexcAFailure}
		STATUS current
		DESCRIPTION
			"No response from exciter A"
	::= {notificationexcA 7}
	
	antennaLoadexcA NOTIFICATION-TYPE    
		OBJECTS {notificationEdge, notificationSeverity, stateantennaLoadexcA}
		STATUS current
		DESCRIPTION
			"Exciter A Antenna or Load"
	::= {notificationexcA 8}

--------------------------------------------------------------------------------------------------------

	inputexcB NOTIFICATION-TYPE    
		OBJECTS {notificationEdge, notificationSeverity, stateinputexcBFailure}
		STATUS current
		DESCRIPTION
			"No input on exciter B"
	::= {notificationexcB 1}
	
	referenceexcB NOTIFICATION-TYPE    
		OBJECTS {notificationEdge, notificationSeverity, statereferenceexcBFailure}
		STATUS current
		DESCRIPTION
			"Exciter B external 10MHz fault"
	::= {notificationexcB 2}
	
	ppsexcB NOTIFICATION-TYPE    
		OBJECTS {notificationEdge, notificationSeverity, stateppsexcBFailure}
		STATUS current
		DESCRIPTION
			"Exciter B pps fault"
	::= {notificationexcB 3}
	
	warningexcB NOTIFICATION-TYPE    
		OBJECTS {notificationEdge, notificationSeverity, statewarningexcBFailure}
		STATUS current
		DESCRIPTION
			"Exciter B WARNING"
	::= {notificationexcB 4}
	
	faultexcB NOTIFICATION-TYPE    
		OBJECTS {notificationEdge, notificationSeverity, statefaultexcBFailure}
		STATUS current
		DESCRIPTION
			"Exciter B FAULT"
	::= {notificationexcB 5}
	
	outputPowerexcBFailure NOTIFICATION-TYPE    
		OBJECTS {notificationEdge, notificationSeverity, stateoutputPowerexcBFailure}
		STATUS current
		DESCRIPTION
			"Exciter B output power FAULT"
	::= {notificationexcB 6}
	
	noResponseexcB NOTIFICATION-TYPE    
		OBJECTS {notificationEdge, notificationSeverity, statenoResponseexcBFailure}
		STATUS current
		DESCRIPTION
			"No response from exciter B"
	::= {notificationexcB 7}
	
	antennaLoadexcB NOTIFICATION-TYPE    
		OBJECTS {notificationEdge, notificationSeverity, stateantennaLoadexcB}
		STATUS current
		DESCRIPTION
			"Exciter B Antenna or Load"
	::= {notificationexcB 8}

--------------------------------------------------------------------------------------------------------

	switchSystemReady NOTIFICATION-TYPE    
		OBJECTS {notificationEdge, notificationSeverity, stateswitchSystemReady}
		STATUS current
		DESCRIPTION
			"Switch System Ready"
	::= {notificationccu 1}
	
	ccuFault NOTIFICATION-TYPE    
		OBJECTS {notificationEdge, notificationSeverity, stateccuFault}
		STATUS current
		DESCRIPTION
			"Fault on CCU"
	::= {notificationccu 2}
	
	interlockFailure NOTIFICATION-TYPE    
		OBJECTS {notificationEdge, notificationSeverity, stateinterlockFailure}
		STATUS current
		DESCRIPTION
			"External coaxial switch interlock"
	::= {notificationccu 3}
	
--------------------------------------------------------------------------------------------------------
	
	gpslockAnotification NOTIFICATION-TYPE    
		OBJECTS {notificationEdge, notificationSeverity, stategpslockAFailure}
		STATUS current
		DESCRIPTION
			"GPS Lock A"
	::= {notificationgps 1}
	
	sfnreadyAnotification NOTIFICATION-TYPE    
		OBJECTS {notificationEdge, notificationSeverity, statesfnreadyAFailure}
		STATUS current
		DESCRIPTION
			"SFN Ready A"
	::= {notificationgps 2}
	
	vccAnotification NOTIFICATION-TYPE    
		OBJECTS {notificationEdge, notificationSeverity, statevccAFailure}
		STATUS current
		DESCRIPTION
			"Vcc A"
	::= {notificationgps 3}
	
	gpslockBnotification NOTIFICATION-TYPE    
		OBJECTS {notificationEdge, notificationSeverity, stategpslockBFailure}
		STATUS current
		DESCRIPTION
			"GPS Lock B"
	::= {notificationgps 4}
	
	sfnreadyBnotification NOTIFICATION-TYPE    
		OBJECTS {notificationEdge, notificationSeverity, statesfnreadyBFailure}
		STATUS current
		DESCRIPTION
			"SFN Ready B"
	::= {notificationgps 5}
	
	vccBnotification NOTIFICATION-TYPE    
		OBJECTS {notificationEdge, notificationSeverity, statevccBFailure}
		STATUS current
		DESCRIPTION
			"Vcc B"
	::= {notificationgps 6}
	
	warningGPS NOTIFICATION-TYPE    
		OBJECTS {notificationEdge, notificationSeverity, statewarningGPS}
		STATUS current
		DESCRIPTION
			"GPS Warning"
	::= {notificationgps 7}
	
	faultGPS NOTIFICATION-TYPE    
		OBJECTS {notificationEdge, notificationSeverity, statefaultGPS}
		STATUS current
		DESCRIPTION
			"GPS Fault"
	::= {notificationgps 8}

	noResponseGPS NOTIFICATION-TYPE    
		OBJECTS {notificationEdge, notificationSeverity, statenoResponseGPS}
		STATUS current
		DESCRIPTION
			"No response from GPS module"
	::= {notificationgps 9}

---------------------------------------------------------------------------
---------------------------------------------------------------------------
    enableinputFailure1 OBJECT-TYPE
      	SYNTAX TruthValue
      	MAX-ACCESS read-write
      	STATUS current
      	DESCRIPTION
        	"Enable/Disable notification:
        		Enable 	(1),
        		Disable (2)"
	::= { enableNotificationstx1 1 }
	
	enablereferenceFailure1 OBJECT-TYPE
      	SYNTAX TruthValue
      	MAX-ACCESS read-write
      	STATUS current
      	DESCRIPTION
        	"Enable/Disable notification:
        		Enable 	(1),
        		Disable (2)"
	::= { enableNotificationstx1 2 }
	
	enableppsFailure1 OBJECT-TYPE
      	SYNTAX TruthValue
      	MAX-ACCESS read-write
      	STATUS current
      	DESCRIPTION
        	"Enable/Disable notification:
        		Enable 	(1),
        		Disable (2)"
	::= { enableNotificationstx1 3 }
	
	enablewarningFailure1 OBJECT-TYPE
      	SYNTAX TruthValue
      	MAX-ACCESS read-write
      	STATUS current
      	DESCRIPTION
        	"Enable/Disable notification:
        		Enable 	(1),
        		Disable (2)"
	::= { enableNotificationstx1 4 }
	
	enablesumfaultFailure1 OBJECT-TYPE
      	SYNTAX TruthValue
      	MAX-ACCESS read-write
      	STATUS current
      	DESCRIPTION
        	"Enable/Disable notification:
        		Enable 	(1),
        		Disable (2)"
	::= { enableNotificationstx1 5 }
	
	enablenoResponseFailure1 OBJECT-TYPE
      	SYNTAX TruthValue
      	MAX-ACCESS read-write
      	STATUS current
      	DESCRIPTION
        	"Enable/Disable notification:
        		Enable 	(1),
        		Disable (2)"
	::= { enableNotificationstx1 6 }
	
	enableantennaLoadFailure1 OBJECT-TYPE
      	SYNTAX TruthValue
      	MAX-ACCESS read-write
      	STATUS current
      	DESCRIPTION
        	"Enable/Disable notification:
        		Enable 	(1),
        		Disable (2)"
	::= { enableNotificationstx1 7 }
	
	enablepoutFailure1 OBJECT-TYPE
      	SYNTAX TruthValue
      	MAX-ACCESS read-write
      	STATUS current
      	DESCRIPTION
        	"Enable/Disable notification:
        		Enable 	(1),
        		Disable (2)"
	::= { enableNotificationstx1 8 }
	
	enablecoaxialswitchFailure1 OBJECT-TYPE
      	SYNTAX TruthValue
      	MAX-ACCESS read-write
      	STATUS current
      	DESCRIPTION
        "Enable/Disable notification:
        		Enable 	(1),
        		Disable (2)"
	::= { enableNotificationstx1 9 }
	
	enableinputFailure2 OBJECT-TYPE
      	SYNTAX TruthValue
      	MAX-ACCESS read-write
      	STATUS current
      	DESCRIPTION
        	"Enable/Disable notification:
        		Enable 	(1),
        		Disable (2)"
	::= { enableNotificationstx2 1 }
	
	enablereferenceFailure2 OBJECT-TYPE
      	SYNTAX TruthValue
      	MAX-ACCESS read-write
      	STATUS current
      	DESCRIPTION
        	"Enable/Disable notification:
        		Enable 	(1),
        		Disable (2)"
	::= { enableNotificationstx2 2 }
	
	enableppsFailure2 OBJECT-TYPE
      	SYNTAX TruthValue
      	MAX-ACCESS read-write
      	STATUS current
      	DESCRIPTION
        	"Enable/Disable notification:
        		Enable 	(1),
        		Disable (2)"
	::= { enableNotificationstx2 3 }
	
	enablewarningFailure2 OBJECT-TYPE
      	SYNTAX TruthValue
      	MAX-ACCESS read-write
      	STATUS current
      	DESCRIPTION
        	"Enable/Disable notification:
        		Enable 	(1),
        		Disable (2)"
	::= { enableNotificationstx2 4 }
	
	enablesumfaultFailure2 OBJECT-TYPE
      	SYNTAX TruthValue
      	MAX-ACCESS read-write
      	STATUS current
      	DESCRIPTION
        	"Enable/Disable notification:
        		Enable 	(1),
        		Disable (2)"
	::= { enableNotificationstx2 5 }
	
	enablenoResponseFailure2 OBJECT-TYPE
      	SYNTAX TruthValue
      	MAX-ACCESS read-write
      	STATUS current
      	DESCRIPTION
        	"Enable/Disable notification:
        		Enable 	(1),
        		Disable (2)"
	::= { enableNotificationstx2 6 }
	
	enableantennaLoadFailure2 OBJECT-TYPE
      	SYNTAX TruthValue
      	MAX-ACCESS read-write
      	STATUS current
      	DESCRIPTION
        	"Enable/Disable notification:
        		Enable 	(1),
        		Disable (2)"
	::= { enableNotificationstx2 7 }
	
	enablepoutFailure2 OBJECT-TYPE
      	SYNTAX TruthValue
      	MAX-ACCESS read-write
      	STATUS current
      	DESCRIPTION
        	"Enable/Disable notification:
        		Enable 	(1),
        		Disable (2)"
	::= { enableNotificationstx2 8 }
	
	enablecoaxialswitchFailure2 OBJECT-TYPE
      	SYNTAX TruthValue
      	MAX-ACCESS read-write
      	STATUS current
      	DESCRIPTION
        	"Enable/Disable notification:
        		Enable 	(1),
        		Disable (2)"
	::= { enableNotificationstx2 9 }
	
	  enableinputFailure3 OBJECT-TYPE
      	SYNTAX TruthValue
      	MAX-ACCESS read-write
      	STATUS current
      	DESCRIPTION
        	"Enable/Disable notification:
        		Enable 	(1),
        		Disable (2)"
	::= { enableNotificationstx3 1 }
	
	enablereferenceFailure3 OBJECT-TYPE
      	SYNTAX TruthValue
      	MAX-ACCESS read-write
      	STATUS current
      	DESCRIPTION
        "Enable/Disable notification:
        		Enable 	(1),
        		Disable (2)"
	::= { enableNotificationstx3 2 }
	
	enableppsFailure3 OBJECT-TYPE
      	SYNTAX TruthValue
      	MAX-ACCESS read-write
      	STATUS current
      	DESCRIPTION
        	"Enable/Disable notification:
        		Enable 	(1),
        		Disable (2)"
	::= { enableNotificationstx3 3 }
	
	enablewarningFailure3 OBJECT-TYPE
      	SYNTAX TruthValue
      	MAX-ACCESS read-write
      	STATUS current
      	DESCRIPTION
        "Enable/Disable notification:
        		Enable 	(1),
        		Disable (2)"
	::= { enableNotificationstx3 4 }
	
	enablesumfaultFailure3 OBJECT-TYPE
      	SYNTAX TruthValue
      	MAX-ACCESS read-write
      	STATUS current
      	DESCRIPTION
        	"Enable/Disable notification:
        		Enable 	(1),
        		Disable (2)"
	::= { enableNotificationstx3 5 }
	
	enablenoResponseFailure3 OBJECT-TYPE
      	SYNTAX TruthValue
      	MAX-ACCESS read-write
      	STATUS current
      	DESCRIPTION
        	"Enable/Disable notification:
        		Enable 	(1),
        		Disable (2)"
	::= { enableNotificationstx3 6 }
	
	enableantennaLoadFailure3 OBJECT-TYPE
      	SYNTAX TruthValue
      	MAX-ACCESS read-write
      	STATUS current
      	DESCRIPTION
        	"Enable/Disable notification:
        		Enable 	(1),
        		Disable (2)"
	::= { enableNotificationstx3 7 }
	
	enablepoutFailure3 OBJECT-TYPE
      	SYNTAX TruthValue
      	MAX-ACCESS read-write
      	STATUS current
      	DESCRIPTION
        	"Enable/Disable notification:
        		Enable 	(1),
        		Disable (2)"
	::= { enableNotificationstx3 8 }
	
	enablecoaxialswitchFailure3 OBJECT-TYPE
      	SYNTAX TruthValue
      	MAX-ACCESS read-write
      	STATUS current
      	DESCRIPTION
        "Enable/Disable notification:
        		Enable 	(1),
        		Disable (2)"
	::= { enableNotificationstx3 9 }
	
	  enableinputFailure4 OBJECT-TYPE
      	SYNTAX TruthValue
      	MAX-ACCESS read-write
      	STATUS current
      	DESCRIPTION
        	"Enable/Disable notification:
        		Enable 	(1),
        		Disable (2)"
	::= { enableNotificationstx4 1 }
	
	enablereferenceFailure4 OBJECT-TYPE
      	SYNTAX TruthValue
      	MAX-ACCESS read-write
      	STATUS current
      	DESCRIPTION
        "Enable/Disable notification:
        		Enable 	(1),
        		Disable (2)"
	::= { enableNotificationstx4 2 }
	
	enableppsFailure4 OBJECT-TYPE
      	SYNTAX TruthValue
      	MAX-ACCESS read-write
      	STATUS current
      	DESCRIPTION
        "Enable/Disable notification:
        		Enable 	(1),
        		Disable (2)"
	::= { enableNotificationstx4 3 }
	
	enablewarningFailure4 OBJECT-TYPE
      	SYNTAX TruthValue
      	MAX-ACCESS read-write
      	STATUS current
      	DESCRIPTION
        	"Enable/Disable notification:
        		Enable 	(1),
        		Disable (2)"
	::= { enableNotificationstx4 4 }
	
	enablesumfaultFailure4 OBJECT-TYPE
      	SYNTAX TruthValue
      	MAX-ACCESS read-write
      	STATUS current
      	DESCRIPTION
        	"Enable/Disable notification:
        		Enable 	(1),
        		Disable (2)"
	::= { enableNotificationstx4 5 }
	
	enablenoResponseFailure4 OBJECT-TYPE
      	SYNTAX TruthValue
      	MAX-ACCESS read-write
      	STATUS current
      	DESCRIPTION
        	"Enable/Disable notification:
        		Enable 	(1),
        		Disable (2)"
	::= { enableNotificationstx4 6 }
	
	enableantennaLoadFailure4 OBJECT-TYPE
      	SYNTAX TruthValue
      	MAX-ACCESS read-write
      	STATUS current
      	DESCRIPTION
        	"Enable/Disable notification:
        		Enable 	(1),
        		Disable (2)"
	::= { enableNotificationstx4 7 }
	
	enablepoutFailure4 OBJECT-TYPE
      	SYNTAX TruthValue
      	MAX-ACCESS read-write
      	STATUS current
      	DESCRIPTION
        	"Enable/Disable notification:
        		Enable 	(1),
        		Disable (2)"
	::= { enableNotificationstx4 8 }
	
	enablecoaxialswitchFailure4 OBJECT-TYPE
      	SYNTAX TruthValue
      	MAX-ACCESS read-write
      	STATUS current
      	DESCRIPTION
        	"Enable/Disable notification:
        		Enable 	(1),
        		Disable (2)"
	::= { enableNotificationstx4 9 }
	
	  enableinputFailure5 OBJECT-TYPE
      	SYNTAX TruthValue
      	MAX-ACCESS read-write
      	STATUS current
      	DESCRIPTION
        	"Enable/Disable notification:
        		Enable 	(1),
        		Disable (2)"
	::= { enableNotificationstx5 1 }
	
	enablereferenceFailure5 OBJECT-TYPE
      	SYNTAX TruthValue
      	MAX-ACCESS read-write
      	STATUS current
      	DESCRIPTION
        	"Enable/Disable notification:
        		Enable 	(1),
        		Disable (2)"
	::= { enableNotificationstx5 2 }
	
	enableppsFailure5 OBJECT-TYPE
      	SYNTAX TruthValue
      	MAX-ACCESS read-write
      	STATUS current
      	DESCRIPTION
        	"Enable/Disable notification:
        		Enable 	(1),
        		Disable (2)"
	::= { enableNotificationstx5 3 }
	
	enablewarningFailure5 OBJECT-TYPE
      	SYNTAX TruthValue
      	MAX-ACCESS read-write
      	STATUS current
      	DESCRIPTION
        	"Enable/Disable notification:
        		Enable 	(1),
        		Disable (2)"
	::= { enableNotificationstx5 4 }
	
	enablesumfaultFailure5 OBJECT-TYPE
      	SYNTAX TruthValue
      	MAX-ACCESS read-write
      	STATUS current
      	DESCRIPTION
        	"Enable/Disable notification:
        		Enable 	(1),
        		Disable (2)"
	::= { enableNotificationstx5 5 }
	
	enablenoResponseFailure5 OBJECT-TYPE
      	SYNTAX TruthValue
      	MAX-ACCESS read-write
      	STATUS current
      	DESCRIPTION
        	"Enable/Disable notification:
        		Enable 	(1),
        		Disable (2)"
	::= { enableNotificationstx5 6 }
	
	enableantennaLoadFailure5 OBJECT-TYPE
      	SYNTAX TruthValue
      	MAX-ACCESS read-write
      	STATUS current
      	DESCRIPTION
        "Enable/Disable notification:
        		Enable 	(1),
        		Disable (2)"
	::= { enableNotificationstx5 7 }
	
	enablepoutFailure5 OBJECT-TYPE
      	SYNTAX TruthValue
      	MAX-ACCESS read-write
      	STATUS current
      	DESCRIPTION
        	"Enable/Disable notification:
        		Enable 	(1),
        		Disable (2)"
	::= { enableNotificationstx5 8 }
	
	enablecoaxialswitchFailure5 OBJECT-TYPE
      	SYNTAX TruthValue
      	MAX-ACCESS read-write
      	STATUS current
      	DESCRIPTION
        	"Enable/Disable notification:
        		Enable 	(1),
        		Disable (2)"
	::= { enableNotificationstx5 9 }
	
	  enableinputFailure6 OBJECT-TYPE
      	SYNTAX TruthValue
      	MAX-ACCESS read-write
      	STATUS current
      	DESCRIPTION
        	"Enable/Disable notification:
        		Enable 	(1),
        		Disable (2)"
	::= { enableNotificationstx6 1 }
	
	enablereferenceFailure6 OBJECT-TYPE
      	SYNTAX TruthValue
      	MAX-ACCESS read-write
      	STATUS current
      	DESCRIPTION
        	"Enable/Disable notification:
        		Enable 	(1),
        		Disable (2)"
	::= { enableNotificationstx6 2 }
	
	enableppsFailure6 OBJECT-TYPE
      	SYNTAX TruthValue
      	MAX-ACCESS read-write
      	STATUS current
      	DESCRIPTION
        "Enable/Disable notification:
        		Enable 	(1),
        		Disable (2)"
	::= { enableNotificationstx6 3 }
	
	enablewarningFailure6 OBJECT-TYPE
      	SYNTAX TruthValue
      	MAX-ACCESS read-write
      	STATUS current
      	DESCRIPTION
        	"Enable/Disable notification:
        		Enable 	(1),
        		Disable (2)"
	::= { enableNotificationstx6 4 }
	
	enablesumfaultFailure6 OBJECT-TYPE
      	SYNTAX TruthValue
      	MAX-ACCESS read-write
      	STATUS current
      	DESCRIPTION
        "Enable/Disable notification:
        		Enable 	(1),
        		Disable (2)"
	::= { enableNotificationstx6 5 }
	
	enablenoResponseFailure6 OBJECT-TYPE
      	SYNTAX TruthValue
      	MAX-ACCESS read-write
      	STATUS current
      	DESCRIPTION
        	"Enable/Disable notification:
        		Enable 	(1),
        		Disable (2)"
	::= { enableNotificationstx6 6 }
	
	enableantennaLoadFailure6 OBJECT-TYPE
      	SYNTAX TruthValue
      	MAX-ACCESS read-write
      	STATUS current
      	DESCRIPTION
        "Enable/Disable notification:
        		Enable 	(1),
        		Disable (2)"
	::= { enableNotificationstx6 7 }
	
	enablepoutFailure6 OBJECT-TYPE
      	SYNTAX TruthValue
      	MAX-ACCESS read-write
      	STATUS current
      	DESCRIPTION
        	"Enable/Disable notification:
        		Enable 	(1),
        		Disable (2)"
	::= { enableNotificationstx6 8 }
	
	enablecoaxialswitchFailure6 OBJECT-TYPE
      	SYNTAX TruthValue
      	MAX-ACCESS read-write
      	STATUS current
      	DESCRIPTION
        	"Enable/Disable notification:
        		Enable 	(1),
        		Disable (2)"
	::= { enableNotificationstx6 9 }
	
	  enableinputFailure7 OBJECT-TYPE
      	SYNTAX TruthValue
      	MAX-ACCESS read-write
      	STATUS current
      	DESCRIPTION
        	"Enable/Disable notification:
        		Enable 	(1),
        		Disable (2)"
	::= { enableNotificationstx7 1 }
	
	enablereferenceFailure7 OBJECT-TYPE
      	SYNTAX TruthValue
      	MAX-ACCESS read-write
      	STATUS current
      	DESCRIPTION
        	"Enable/Disable notification:
        		Enable 	(1),
        		Disable (2)"
	::= { enableNotificationstx7 2 }
	
	enableppsFailure7 OBJECT-TYPE
      	SYNTAX TruthValue
      	MAX-ACCESS read-write
      	STATUS current
      	DESCRIPTION
        	"Enable/Disable notification:
        		Enable 	(1),
        		Disable (2)"
	::= { enableNotificationstx7 3 }
	
	enablewarningFailure7 OBJECT-TYPE
      	SYNTAX TruthValue
      	MAX-ACCESS read-write
      	STATUS current
      	DESCRIPTION
        	"Enable/Disable notification:
        		Enable 	(1),
        		Disable (2)"
	::= { enableNotificationstx7 4 }
	
	enablesumfaultFailure7 OBJECT-TYPE
      	SYNTAX TruthValue
      	MAX-ACCESS read-write
      	STATUS current
      	DESCRIPTION
        "Enable/Disable notification:
        		Enable 	(1),
        		Disable (2)"
	::= { enableNotificationstx7 5 }
	
	enablenoResponseFailure7 OBJECT-TYPE
      	SYNTAX TruthValue
      	MAX-ACCESS read-write
      	STATUS current
      	DESCRIPTION
        	"Enable/Disable notification:
        		Enable 	(1),
        		Disable (2)"
	::= { enableNotificationstx7 6 }
	
	enableantennaLoadFailure7 OBJECT-TYPE
      	SYNTAX TruthValue
      	MAX-ACCESS read-write
      	STATUS current
      	DESCRIPTION
        	"Enable/Disable notification:
        		Enable 	(1),
        		Disable (2)"
	::= { enableNotificationstx7 7 }
	
	enablepoutFailure7 OBJECT-TYPE
      	SYNTAX TruthValue
      	MAX-ACCESS read-write
      	STATUS current
      	DESCRIPTION
        "Enable/Disable notification:
        		Enable 	(1),
        		Disable (2)"
	::= { enableNotificationstx7 8 }
	
	enablecoaxialswitchFailure7 OBJECT-TYPE
      	SYNTAX TruthValue
      	MAX-ACCESS read-write
      	STATUS current
      	DESCRIPTION
        	"Enable/Disable notification:
        		Enable 	(1),
        		Disable (2)"
	::= { enableNotificationstx7 9 }
	
	  enableinputFailure8 OBJECT-TYPE
      	SYNTAX TruthValue
      	MAX-ACCESS read-write
      	STATUS current
      	DESCRIPTION
        	"Enable/Disable notification:
        		Enable 	(1),
        		Disable (2)"
	::= { enableNotificationstx8 1 }
	
	enablereferenceFailure8 OBJECT-TYPE
      	SYNTAX TruthValue
      	MAX-ACCESS read-write
      	STATUS current
      	DESCRIPTION
        	"Enable/Disable notification:
        		Enable 	(1),
        		Disable (2)"
	::= { enableNotificationstx8 2 }
	
	enableppsFailure8 OBJECT-TYPE
      	SYNTAX TruthValue
      	MAX-ACCESS read-write
      	STATUS current
      	DESCRIPTION
        	"Enable/Disable notification:
        		Enable 	(1),
        		Disable (2)"
	::= { enableNotificationstx8 3 }
	
	enablewarningFailure8 OBJECT-TYPE
      	SYNTAX TruthValue
      	MAX-ACCESS read-write
      	STATUS current
      	DESCRIPTION
        	"Enable/Disable notification:
        		Enable 	(1),
        		Disable (2)"
	::= { enableNotificationstx8 4 }
	
	enablesumfaultFailure8 OBJECT-TYPE
      	SYNTAX TruthValue
      	MAX-ACCESS read-write
      	STATUS current
      	DESCRIPTION
        	"Enable/Disable notification:
        		Enable 	(1),
        		Disable (2)"
	::= { enableNotificationstx8 5 }
	
	enablenoResponseFailure8 OBJECT-TYPE
      	SYNTAX TruthValue
      	MAX-ACCESS read-write
      	STATUS current
      	DESCRIPTION
        	"Enable/Disable notification:
        		Enable 	(1),
        		Disable (2)"
	::= { enableNotificationstx8 6 }
	
	enableantennaLoadFailure8 OBJECT-TYPE
      	SYNTAX TruthValue
      	MAX-ACCESS read-write
      	STATUS current
      	DESCRIPTION
        	"Enable/Disable notification:
        		Enable 	(1),
        		Disable (2)"
	::= { enableNotificationstx8 7 }
	
	enablepoutFailure8 OBJECT-TYPE
      	SYNTAX TruthValue
      	MAX-ACCESS read-write
      	STATUS current
      	DESCRIPTION
        	"Enable/Disable notification:
        		Enable 	(1),
        		Disable (2)"
	::= { enableNotificationstx8 8 }
	
	enablecoaxialswitchFailure8 OBJECT-TYPE
      	SYNTAX TruthValue
      	MAX-ACCESS read-write
      	STATUS current
      	DESCRIPTION
        	"Enable/Disable notification:
        		Enable 	(1),
        		Disable (2)"
	::= { enableNotificationstx8 9 }
	
	  enableinputFailureR OBJECT-TYPE
      	SYNTAX TruthValue
      	MAX-ACCESS read-write
      	STATUS current
      	DESCRIPTION
        	"Enable/Disable notification:
        		Enable 	(1),
        		Disable (2)"
	::= { enableNotificationstxR 1 }
	
	enablereferenceFailureR OBJECT-TYPE
      	SYNTAX TruthValue
      	MAX-ACCESS read-write
      	STATUS current
      	DESCRIPTION
	     "Enable/Disable notification:
	      		Enable 	(1),
	      		Disable (2)"
	::= { enableNotificationstxR 2 }
	
	enableppsFailureR OBJECT-TYPE
      	SYNTAX TruthValue
      	MAX-ACCESS read-write
      	STATUS current
      	DESCRIPTION
        	"Enable/Disable notification:
        		Enable 	(1),
        		Disable (2)"
	::= { enableNotificationstxR 3 }
	
	enablewarningFailureR OBJECT-TYPE
      	SYNTAX TruthValue
      	MAX-ACCESS read-write
      	STATUS current
      	DESCRIPTION
        	"Enable/Disable notification:
        		Enable 	(1),
        		Disable (2)"
	::= { enableNotificationstxR 4 }
	
	enablesumfaultFailureR OBJECT-TYPE
      	SYNTAX TruthValue
      	MAX-ACCESS read-write
      	STATUS current
      	DESCRIPTION
        	"Enable/Disable notification:
        		Enable 	(1),
        		Disable (2)"
	::= { enableNotificationstxR 5 }
	
	enablenoResponseFailureR OBJECT-TYPE
      	SYNTAX TruthValue
      	MAX-ACCESS read-write
      	STATUS current
      	DESCRIPTION
        	"Enable/Disable notification:
        		Enable 	(1),
        		Disable (2)"
	::= { enableNotificationstxR 6 }
	
	enableantennaLoadFailureR OBJECT-TYPE
      	SYNTAX TruthValue
      	MAX-ACCESS read-write
      	STATUS current
      	DESCRIPTION
        	"Enable/Disable notification:
        		Enable 	(1),
        		Disable (2)"
	::= { enableNotificationstxR 7 }
	
	enablepoutFailureR OBJECT-TYPE
      	SYNTAX TruthValue
      	MAX-ACCESS read-write
      	STATUS current
      	DESCRIPTION
        	"Enable/Disable notification:
        		Enable 	(1),
        		Disable (2)"
	::= { enableNotificationstxR 8 }

--------------------------------------------------------------------------	

	enablenoResponseMatrix OBJECT-TYPE
      	SYNTAX TruthValue
      	MAX-ACCESS read-write
      	STATUS current
      	DESCRIPTION
        	"Enable/Disable notification:
        		Enable 	(1),
        		Disable (2)"
	::= { enableNotificationsMatrix 1 }

--------------------------------------------------------------------------	

	enablepoutFailure OBJECT-TYPE
      	SYNTAX TruthValue
      	MAX-ACCESS read-write
      	STATUS current
      	DESCRIPTION
        	"Enable/Disable notification:
        		Enable 	(1),
        		Disable (2)"
	::= { enableNotificationspower 1 }
	
	enablereflectedFailure OBJECT-TYPE
      	SYNTAX TruthValue
      	MAX-ACCESS read-write
      	STATUS current
      	DESCRIPTION
        	"Enable/Disable notification:
        		Enable 	(1),
        		Disable (2)"
	::= { enableNotificationspower 2 }

--------------------------------------------------------------------------	

	enabletemperatureFailure OBJECT-TYPE
      	SYNTAX TruthValue
      	MAX-ACCESS read-write
      	STATUS current
      	DESCRIPTION
        "Enable/Disable notification:
        		Enable 	(1),
        		Disable (2)"
	::= { enableNotificationsrack 1 }
	
	enableturbine1 OBJECT-TYPE
      	SYNTAX TruthValue
      	MAX-ACCESS read-write
      	STATUS current
      	DESCRIPTION
        "Enable/Disable notification:
        		Enable 	(1),
        		Disable (2)"
	::= { enableNotificationsrack 2 }
	
	enableturbine2 OBJECT-TYPE
      	SYNTAX TruthValue
      	MAX-ACCESS read-write
      	STATUS current
      	DESCRIPTION
        	"Enable/Disable notification:
        		Enable 	(1),
        		Disable (2)"
	::= { enableNotificationsrack 3 }
	
	enablecoaxialswitch OBJECT-TYPE
      	SYNTAX TruthValue
      	MAX-ACCESS read-write
      	STATUS current
      	DESCRIPTION
        	"Enable/Disable notification:
        		Enable 	(1),
        		Disable (2)"
	::= { enableNotificationsrack 4 }
	
	enableamplifier OBJECT-TYPE
      	SYNTAX TruthValue
      	MAX-ACCESS read-write
      	STATUS current
      	DESCRIPTION
        "Enable/Disable notification:
        		Enable 	(1),
        		Disable (2)"
	::= { enableNotificationsrack 5 }
	
	enablepowersupply OBJECT-TYPE
      	SYNTAX TruthValue
      	MAX-ACCESS read-write
      	STATUS current
      	DESCRIPTION
        	"Enable/Disable notification:
        		Enable 	(1),
        		Disable (2)"
	::= { enableNotificationsrack 6 }

	enableflow1Faultrack1 OBJECT-TYPE
      	SYNTAX TruthValue
      	MAX-ACCESS read-write
      	STATUS current
      	DESCRIPTION
        	"Enable/Disable notification:
        		Enable 	(1),
        		Disable (2)"
	::= { enableNotificationsrack 7 }
	
	enableflow2Faultrack1 OBJECT-TYPE
      	SYNTAX TruthValue
      	MAX-ACCESS read-write
      	STATUS current
      	DESCRIPTION
        	"Enable/Disable notification:
        		Enable 	(1),
        		Disable (2)"
	::= { enableNotificationsrack 8 }
	
	enablePumpsLinkrack1 OBJECT-TYPE
      	SYNTAX TruthValue
      	MAX-ACCESS read-write
      	STATUS current
      	DESCRIPTION
        	"Enable/Disable notification:
        		Enable 	(1),
        		Disable (2)"
	::= { enableNotificationsrack 9 }
	
	enableSecLooprack1 OBJECT-TYPE
      	SYNTAX TruthValue
      	MAX-ACCESS read-write
      	STATUS current
      	DESCRIPTION
        	"Enable/Disable notification:
        		Enable 	(1),
        		Disable (2)"
	::= { enableNotificationsrack 10 }
	
	enableMainLooprack1 OBJECT-TYPE
      	SYNTAX TruthValue
      	MAX-ACCESS read-write
      	STATUS current
      	DESCRIPTION
        	"Enable/Disable notification:
        		Enable 	(1),
        		Disable (2)"
	::= { enableNotificationsrack 11 }
	
	enableAuxPowerrack1 OBJECT-TYPE
      	SYNTAX TruthValue
      	MAX-ACCESS read-write
      	STATUS current
      	DESCRIPTION
        	"Enable/Disable notification:
        		Enable 	(1),
        		Disable (2)"
	::= { enableNotificationsrack 12 }
	
	enableCoolingrack1 OBJECT-TYPE
      	SYNTAX TruthValue
      	MAX-ACCESS read-write
      	STATUS current
      	DESCRIPTION
        	"Enable/Disable notification:
        		Enable 	(1),
        		Disable (2)"
	::= { enableNotificationsrack 13 }
	
	enablePressureFaultrack1 OBJECT-TYPE
      	SYNTAX TruthValue
      	MAX-ACCESS read-write
      	STATUS current
      	DESCRIPTION
        	"Enable/Disable notification:
        		Enable 	(1),
        		Disable (2)"
	::= { enableNotificationsrack 14 }
	
	enableCoolingPowerrack1 OBJECT-TYPE
      	SYNTAX TruthValue
      	MAX-ACCESS read-write
      	STATUS current
      	DESCRIPTION
        	"Enable/Disable notification:
        		Enable 	(1),
        		Disable (2)"
	::= { enableNotificationsrack 15 }
	
	enableExchangeFan1Comrack1 OBJECT-TYPE
      	SYNTAX TruthValue
      	MAX-ACCESS read-write
      	STATUS current
      	DESCRIPTION
        	"Enable/Disable notification:
        		Enable 	(1),
        		Disable (2)"
	::= { enableNotificationsrack 16 }
	
	enableExchangeFan2Comrack1 OBJECT-TYPE
      	SYNTAX TruthValue
      	MAX-ACCESS read-write
      	STATUS current
      	DESCRIPTION
        	"Enable/Disable notification:
        		Enable 	(1),
        		Disable (2)"
	::= { enableNotificationsrack 17 }
	
	enablePump1Faultrack1 OBJECT-TYPE
      	SYNTAX TruthValue
      	MAX-ACCESS read-write
      	STATUS current
      	DESCRIPTION
        	"Enable/Disable notification:
        		Enable 	(1),
        		Disable (2)"
	::= { enableNotificationsrack 18 }
	
	enablePump2Faultrack1 OBJECT-TYPE
      	SYNTAX TruthValue
      	MAX-ACCESS read-write
      	STATUS current
      	DESCRIPTION
        	"Enable/Disable notification:
        		Enable 	(1),
        		Disable (2)"
	::= { enableNotificationsrack 19 }
	
	enableExchangeFan1Faultrack1 OBJECT-TYPE
      	SYNTAX TruthValue
      	MAX-ACCESS read-write
      	STATUS current
      	DESCRIPTION
        	"Enable/Disable notification:
        		Enable 	(1),
        		Disable (2)"
	::= { enableNotificationsrack 20 }
	
	enableExchangeFan2Faultrack1 OBJECT-TYPE
      	SYNTAX TruthValue
      	MAX-ACCESS read-write
      	STATUS current
      	DESCRIPTION
        	"Enable/Disable notification:
        		Enable 	(1),
        		Disable (2)"
	::= { enableNotificationsrack 21 }
	
	enableExchangeLinkrack1 OBJECT-TYPE
      	SYNTAX TruthValue
      	MAX-ACCESS read-write
      	STATUS current
      	DESCRIPTION
        	"Enable/Disable notification:
        		Enable 	(1),
        		Disable (2)"
	::= { enableNotificationsrack 22 }
	
	enableExchangePowerrack1 OBJECT-TYPE
      	SYNTAX TruthValue
      	MAX-ACCESS read-write
      	STATUS current
      	DESCRIPTION
        	"Enable/Disable notification:
        		Enable 	(1),
        		Disable (2)"
	::= { enableNotificationsrack 23 }
	
	enablePump1Linkrack1 OBJECT-TYPE
      	SYNTAX TruthValue
      	MAX-ACCESS read-write
      	STATUS current
      	DESCRIPTION
        	"Enable/Disable notification:
        		Enable 	(1),
        		Disable (2)"
	::= { enableNotificationsrack 24 }
	
	enablePump2Linkrack1 OBJECT-TYPE
      	SYNTAX TruthValue
      	MAX-ACCESS read-write
      	STATUS current
      	DESCRIPTION
        	"Enable/Disable notification:
        		Enable 	(1),
        		Disable (2)"
	::= { enableNotificationsrack 25 }
	
	enableflow1Faultrack2 OBJECT-TYPE
      	SYNTAX TruthValue
      	MAX-ACCESS read-write
      	STATUS current
      	DESCRIPTION
        	"Enable/Disable notification:
        		Enable 	(1),
        		Disable (2)"
	::= { enableNotificationsrack 26 }
	
	enableflow2Faultrack2 OBJECT-TYPE
      	SYNTAX TruthValue
      	MAX-ACCESS read-write
      	STATUS current
      	DESCRIPTION
        	"Enable/Disable notification:
        		Enable 	(1),
        		Disable (2)"
	::= { enableNotificationsrack 27 }
	
	enablePumpsLinkrack2 OBJECT-TYPE
      	SYNTAX TruthValue
      	MAX-ACCESS read-write
      	STATUS current
      	DESCRIPTION
        	"Enable/Disable notification:
        		Enable 	(1),
        		Disable (2)"
	::= { enableNotificationsrack 28 }
	
	enableSecLooprack2 OBJECT-TYPE
      	SYNTAX TruthValue
      	MAX-ACCESS read-write
      	STATUS current
      	DESCRIPTION
        	"Enable/Disable notification:
        		Enable 	(1),
        		Disable (2)"
	::= { enableNotificationsrack 29 }
	
	enableMainLooprack2 OBJECT-TYPE
      	SYNTAX TruthValue
      	MAX-ACCESS read-write
      	STATUS current
      	DESCRIPTION
        	"Enable/Disable notification:
        		Enable 	(1),
        		Disable (2)"
	::= { enableNotificationsrack 30 }
	
	enableAuxPowerrack2 OBJECT-TYPE
      	SYNTAX TruthValue
      	MAX-ACCESS read-write
      	STATUS current
      	DESCRIPTION
        	"Enable/Disable notification:
        		Enable 	(1),
        		Disable (2)"
	::= { enableNotificationsrack 31 }
	
	enableCoolingrack2 OBJECT-TYPE
      	SYNTAX TruthValue
      	MAX-ACCESS read-write
      	STATUS current
      	DESCRIPTION
        	"Enable/Disable notification:
        		Enable 	(1),
        		Disable (2)"
	::= { enableNotificationsrack 32 }
	
	enablePressureFaultrack2 OBJECT-TYPE
      	SYNTAX TruthValue
      	MAX-ACCESS read-write
      	STATUS current
      	DESCRIPTION
        	"Enable/Disable notification:
        		Enable 	(1),
        		Disable (2)"
	::= { enableNotificationsrack 33 }
	
	enableCoolingPowerrack2 OBJECT-TYPE
      	SYNTAX TruthValue
      	MAX-ACCESS read-write
      	STATUS current
      	DESCRIPTION
        	"Enable/Disable notification:
        		Enable 	(1),
        		Disable (2)"
	::= { enableNotificationsrack 34 }
	
	enableExchangeFan1Comrack2 OBJECT-TYPE
      	SYNTAX TruthValue
      	MAX-ACCESS read-write
      	STATUS current
      	DESCRIPTION
        	"Enable/Disable notification:
        		Enable 	(1),
        		Disable (2)"
	::= { enableNotificationsrack 35 }
	
	enableExchangeFan2Comrack2 OBJECT-TYPE
      	SYNTAX TruthValue
      	MAX-ACCESS read-write
      	STATUS current
      	DESCRIPTION
        	"Enable/Disable notification:
        		Enable 	(1),
        		Disable (2)"
	::= { enableNotificationsrack 36 }
	
	enablePump1Faultrack2 OBJECT-TYPE
      	SYNTAX TruthValue
      	MAX-ACCESS read-write
      	STATUS current
      	DESCRIPTION
        	"Enable/Disable notification:
        		Enable 	(1),
        		Disable (2)"
	::= { enableNotificationsrack 37 }
	
	enablePump2Faultrack2 OBJECT-TYPE
      	SYNTAX TruthValue
      	MAX-ACCESS read-write
      	STATUS current
      	DESCRIPTION
        	"Enable/Disable notification:
        		Enable 	(1),
        		Disable (2)"
	::= { enableNotificationsrack 38 }
	
	enableExchangeFan1Faultrack2 OBJECT-TYPE
      	SYNTAX TruthValue
      	MAX-ACCESS read-write
      	STATUS current
      	DESCRIPTION
        	"Enable/Disable notification:
        		Enable 	(1),
        		Disable (2)"
	::= { enableNotificationsrack 39 }
	
	enableExchangeFan2Faultrack2 OBJECT-TYPE
      	SYNTAX TruthValue
      	MAX-ACCESS read-write
      	STATUS current
      	DESCRIPTION
        	"Enable/Disable notification:
        		Enable 	(1),
        		Disable (2)"
	::= { enableNotificationsrack 40 }
	
	enableExchangeLinkrack2 OBJECT-TYPE
      	SYNTAX TruthValue
      	MAX-ACCESS read-write
      	STATUS current
      	DESCRIPTION
        	"Enable/Disable notification:
        		Enable 	(1),
        		Disable (2)"
	::= { enableNotificationsrack 41 }
	
	enableExchangePowerrack2 OBJECT-TYPE
      	SYNTAX TruthValue
      	MAX-ACCESS read-write
      	STATUS current
      	DESCRIPTION
        	"Enable/Disable notification:
        		Enable 	(1),
        		Disable (2)"
	::= { enableNotificationsrack 42 }
	
	enablePump1Linkrack2 OBJECT-TYPE
      	SYNTAX TruthValue
      	MAX-ACCESS read-write
      	STATUS current
      	DESCRIPTION
        	"Enable/Disable notification:
        		Enable 	(1),
        		Disable (2)"
	::= { enableNotificationsrack 43 }
	
	enablePump2Linkrack2 OBJECT-TYPE
      	SYNTAX TruthValue
      	MAX-ACCESS read-write
      	STATUS current
      	DESCRIPTION
        	"Enable/Disable notification:
        		Enable 	(1),
        		Disable (2)"
	::= { enableNotificationsrack 44 }
--------------------------------------------------------------------------	

	enableinputexcA OBJECT-TYPE
      	SYNTAX TruthValue
      	MAX-ACCESS read-write
      	STATUS current
      	DESCRIPTION
        	"Enable/Disable notification:
        		Enable 	(1),
        		Disable (2)"
	::= { enableNotificationsexcA 1 }
	
	enablereferenceexcA OBJECT-TYPE
      	SYNTAX TruthValue
      	MAX-ACCESS read-write
      	STATUS current
      	DESCRIPTION
        	"Enable/Disable notification:
        		Enable 	(1),
        		Disable (2)"
	::= { enableNotificationsexcA 2 }
	
	enableppsexcA OBJECT-TYPE
      	SYNTAX TruthValue
      	MAX-ACCESS read-write
      	STATUS current
      	DESCRIPTION
        "Enable/Disable notification:
        		Enable 	(1),
        		Disable (2)"
	::= { enableNotificationsexcA 3 }
	
	enablewarningexcA OBJECT-TYPE
      	SYNTAX TruthValue
      	MAX-ACCESS read-write
      	STATUS current
      	DESCRIPTION
        	"Enable/Disable notification:
        		Enable 	(1),
        		Disable (2)"
	::= { enableNotificationsexcA 4 }
	
	enablefaultexcA OBJECT-TYPE
      	SYNTAX TruthValue
      	MAX-ACCESS read-write
      	STATUS current
      	DESCRIPTION
        	"Enable/Disable notification:
        		Enable 	(1),
        		Disable (2)"
	::= { enableNotificationsexcA 5 }
	
	enableoutputPowerexcAFailure OBJECT-TYPE
      	SYNTAX TruthValue
      	MAX-ACCESS read-write
      	STATUS current
      	DESCRIPTION
        "Enable/Disable notification:
        		Enable 	(1),
        		Disable (2)"
	::= { enableNotificationsexcA 6 }
	
	enablenoResponseexcA OBJECT-TYPE
      	SYNTAX TruthValue
      	MAX-ACCESS read-write
      	STATUS current
      	DESCRIPTION
        	"Enable/Disable notification:
        		Enable 	(1),
        		Disable (2)"
	::= { enableNotificationsexcA 7 }
	
	enableantennaLoadexcA OBJECT-TYPE
      	SYNTAX TruthValue
      	MAX-ACCESS read-write
      	STATUS current
      	DESCRIPTION
        	"Enable/Disable notification:
        		Enable 	(1),
        		Disable (2)"
	::= { enableNotificationsexcA 8 }

--------------------------------------------------------------------------	

	enableinputexcB OBJECT-TYPE
      	SYNTAX TruthValue
      	MAX-ACCESS read-write
      	STATUS current
      	DESCRIPTION
        	"Enable/Disable notification:
        		Enable 	(1),
        		Disable (2)"
	::= { enableNotificationsexcB 1 }
	
	enablereferenceexcB OBJECT-TYPE
      	SYNTAX TruthValue
      	MAX-ACCESS read-write
      	STATUS current
      	DESCRIPTION
        	"Enable/Disable notification:
        		Enable 	(1),
        		Disable (2)"
	::= { enableNotificationsexcB 2 }
	
	enableppsexcB OBJECT-TYPE
      	SYNTAX TruthValue
      	MAX-ACCESS read-write
      	STATUS current
      	DESCRIPTION
        	"Enable/Disable notification:
        		Enable 	(1),
        		Disable (2)"
	::= { enableNotificationsexcB 3 }
	
	enablewarningexcB OBJECT-TYPE
      	SYNTAX TruthValue
      	MAX-ACCESS read-write
      	STATUS current
      	DESCRIPTION
        	"Enable/Disable notification:
        		Enable 	(1),
        		Disable (2)"
	::= { enableNotificationsexcB 4 }
	
	enablefaultexcB OBJECT-TYPE
      	SYNTAX TruthValue
      	MAX-ACCESS read-write
      	STATUS current
      	DESCRIPTION
        	"Enable/Disable notification:
        		Enable 	(1),
        		Disable (2)"
	::= { enableNotificationsexcB 5 }
	
	enableoutputPowerexcBFailure OBJECT-TYPE
      	SYNTAX TruthValue
      	MAX-ACCESS read-write
      	STATUS current
      	DESCRIPTION
        	"Enable/Disable notification:
        		Enable 	(1),
        		Disable (2)"
	::= { enableNotificationsexcB 6 }
	
	enablenoResponseexcB OBJECT-TYPE
      	SYNTAX TruthValue
      	MAX-ACCESS read-write
      	STATUS current
      	DESCRIPTION
        	"Enable/Disable notification:
        		Enable 	(1),
        		Disable (2)"
	::= { enableNotificationsexcB 7 }
	
	enableantennaLoadexcB OBJECT-TYPE
      	SYNTAX TruthValue
      	MAX-ACCESS read-write
      	STATUS current
      	DESCRIPTION
        	"Enable/Disable notification:
        		Enable 	(1),
        		Disable (2)"
	::= { enableNotificationsexcB 8 }

--------------------------------------------------------------------------	

	enableswitchSystemReady OBJECT-TYPE
      	SYNTAX TruthValue
      	MAX-ACCESS read-write
      	STATUS current
      	DESCRIPTION
        	"Enable/Disable notification:
        		Enable 	(1),
        		Disable (2)"
	::= { enableNotificationsccu 1 }
	
	enableccuFault OBJECT-TYPE
      	SYNTAX TruthValue
      	MAX-ACCESS read-write
      	STATUS current
      	DESCRIPTION
        	"Enable/Disable notification:
        		Enable 	(1),
        		Disable (2)"
	::= { enableNotificationsccu 2 }
	
	enableinterlockFailure OBJECT-TYPE
      	SYNTAX TruthValue
      	MAX-ACCESS read-write
      	STATUS current
      	DESCRIPTION
        	"Enable/Disable notification:
        		Enable 	(1),
        		Disable (2)"
	::= { enableNotificationsccu 3 }
	
--------------------------------------------------------------------------	
	
	enablegpslockA OBJECT-TYPE
      	SYNTAX TruthValue
      	MAX-ACCESS read-write
      	STATUS current
      	DESCRIPTION
        	"Enable/Disable notification:
        		Enable 	(1),
        		Disable (2)"
	::= { enableNotificationsgps 1 }
	
	enablesfnreadyA OBJECT-TYPE
      	SYNTAX TruthValue
      	MAX-ACCESS read-write
      	STATUS current
      	DESCRIPTION
        	"Enable/Disable notification:
        		Enable 	(1),
        		Disable (2)"
	::= { enableNotificationsgps 2 }
	
	enablevccA OBJECT-TYPE
      	SYNTAX TruthValue
      	MAX-ACCESS read-write
      	STATUS current
      	DESCRIPTION
        	"Enable/Disable notification:
        		Enable 	(1),
        		Disable (2)"
	::= { enableNotificationsgps 3 }
	
	enablegpslockB OBJECT-TYPE
      	SYNTAX TruthValue
      	MAX-ACCESS read-write
      	STATUS current
      	DESCRIPTION
        	"Enable/Disable notification:
        		Enable 	(1),
        		Disable (2)"
	::= { enableNotificationsgps 4 }
	
	enablesfnreadyB OBJECT-TYPE
      	SYNTAX TruthValue
      	MAX-ACCESS read-write
      	STATUS current
      	DESCRIPTION
        	"Enable/Disable notification:
        		Enable 	(1),
        		Disable (2)"
	::= { enableNotificationsgps 5 }
	
	enablevccB OBJECT-TYPE
      	SYNTAX TruthValue
      	MAX-ACCESS read-write
      	STATUS current
      	DESCRIPTION
        	"Enable/Disable notification:
        		Enable 	(1),
        		Disable (2)"
	::= { enableNotificationsgps 6 }
	
	enablewarningGPS OBJECT-TYPE
      	SYNTAX TruthValue
      	MAX-ACCESS read-write
      	STATUS current
      	DESCRIPTION
        	"Enable/Disable notification:
        		Enable 	(1),
        		Disable (2)"
	::= { enableNotificationsgps 7 }
	
	enablefaultGPS OBJECT-TYPE
      	SYNTAX TruthValue
      	MAX-ACCESS read-write
      	STATUS current
      	DESCRIPTION
        	"Enable/Disable notification:
        		Enable 	(1),
        		Disable (2)"
	::= { enableNotificationsgps 8 }
	
	enablenoResponseGPS OBJECT-TYPE
      	SYNTAX TruthValue
      	MAX-ACCESS read-write
      	STATUS current
      	DESCRIPTION
        	"Enable/Disable notification:
        		Enable 	(1),
        		Disable (2)"
	::= { enableNotificationsgps 9 }
	
-----------------------------------------------------------------------------------                          
-----------------------------------------------------------------------------------                                                                                                                                                             
notificationHistorical OBJECT IDENTIFIER ::={ccu9000 12}

	trapsTable OBJECT-TYPE
		SYNTAX SEQUENCE OF EntryTable
		MAX-ACCESS not-accessible
		STATUS current
		DESCRIPTION
			"List of last 100 notification events"
	::= {notificationHistorical 1}
		
	entryTable OBJECT-TYPE
		SYNTAX EntryTable
		MAX-ACCESS	not-accessible
		STATUS current
		DESCRIPTION
			"An entry (row) in the trap (notification) table"
		INDEX {indexTable}
	::= {trapsTable 1}	
	
------------------------------------------------------------------------
EntryTable ::= 

	SEQUENCE 
		{
			indexTable Integer32,
			codeTable Integer32,
			dateTable DisplayString,
			timeTable DisplayString
        }
        
	indexTable OBJECT-TYPE
		SYNTAX Integer32 (1..100)
		MAX-ACCESS not-accessible
		STATUS current
		DESCRIPTION
			"Variable for identifying instances of columnar objects in trap (notification) table"
	::={entryTable 1}
	
	codeTable OBJECT-TYPE
		SYNTAX Integer32
		MAX-ACCESS read-only
		STATUS current
		DESCRIPTION
			"Notification trap number (ABC)
			[ A: TX number (9:Reserve); 
			  B: 0 or 1 =>alarm entry, 2 =>alarm clear; 
			  C: alarm code;]"
	::={entryTable 2}

	dateTable OBJECT-TYPE
		SYNTAX DisplayString (SIZE(5))
		MAX-ACCESS read-only
		STATUS current
		DESCRIPTION
			"Notification date"
	::={entryTable 3}

	timeTable OBJECT-TYPE
		SYNTAX DisplayString (SIZE(5))
		MAX-ACCESS read-only
		STATUS current
		DESCRIPTION
			"Notification time"
	::= {entryTable 4}           
                             
	indexTab OBJECT-TYPE	
		SYNTAX Integer32 
		MAX-ACCESS read-only
		STATUS current
		DESCRIPTION
			"Index of most recent notification in trap table"
	::= {notificationHistorical 2}
	                               
------------------------------------------------------------------------------------                                     
	groupTrapsTable OBJECT-GROUP
		OBJECTS 
			{
				codeTable,
				 dateTable,
				 timeTable, 
				 indexTab
			}
		STATUS current
		DESCRIPTION
			"Traps Table Group"
	::= {mibGroups 39}                        
---------------------------------------------------------------------------
---------------------------------------------------------------------------
    stateinputFailure1 OBJECT-TYPE
      	SYNTAX TruthValue
      	MAX-ACCESS read-only
      	STATUS current
      	DESCRIPTION
        	"Failure Active/Inactive:
        		active (1)   --> failure
        		inactive (2) --> no failure"
	::= { stateNotificationstx1 1 }
	
	statereferenceFailure1 OBJECT-TYPE
      	SYNTAX TruthValue
      	MAX-ACCESS read-only
      	STATUS current
      	DESCRIPTION
        	"Failure Active/Inactive:
        		active (1)   --> failure
        		inactive (2) --> no failure"
	::= { stateNotificationstx1 2 }
	
	stateppsFailure1 OBJECT-TYPE
      	SYNTAX TruthValue
      	MAX-ACCESS read-only
      	STATUS current
      	DESCRIPTION
        	"Failure Active/Inactive:
        		active (1)   --> failure
        		inactive (2) --> no failure"
	::= { stateNotificationstx1 3 }
	
	statewarningFailure1 OBJECT-TYPE
      	SYNTAX TruthValue
      	MAX-ACCESS read-only
      	STATUS current
      	DESCRIPTION
        	"Failure Active/Inactive:
        		active (1)   --> failure
        		inactive (2) --> no failure"
	::= { stateNotificationstx1 4 }
	
	statesumfaultFailure1 OBJECT-TYPE
      	SYNTAX TruthValue
      	MAX-ACCESS read-only
      	STATUS current
      	DESCRIPTION
        	"Failure Active/Inactive:
        		active (1)   --> failure
        		inactive (2) --> no failure"
	::= { stateNotificationstx1 5 }
	
	statenoResponseFailure1 OBJECT-TYPE
      	SYNTAX TruthValue
      	MAX-ACCESS read-only
      	STATUS current
      	DESCRIPTION
        	"Failure Active/Inactive:
        		active (1)   --> failure
        		inactive (2) --> no failure"
	::= { stateNotificationstx1 6 }
	
	stateantennaLoadFailure1 OBJECT-TYPE
      	SYNTAX TruthValue
      	MAX-ACCESS read-only
      	STATUS current
      	DESCRIPTION
        	"Failure Active/Inactive:
        		active (1)   --> Load
        		inactive (2) --> Antena"
	::= { stateNotificationstx1 7 }
	
	statepoutFailure1 OBJECT-TYPE
      	SYNTAX TruthValue
      	MAX-ACCESS read-only
      	STATUS current
      	DESCRIPTION
        	"Failure Active/Inactive:
        		active (1)   --> failure
        		inactive (2) --> no failure"
	::= { stateNotificationstx1 8 }
	
	statecoaxialswitchFailure1 OBJECT-TYPE
      	SYNTAX TruthValue
      	MAX-ACCESS read-only
      	STATUS current
      	DESCRIPTION
        	"Failure Active/Inactive:
        		active (1)   --> failure
        		inactive (2) --> no failure"
	::= { stateNotificationstx1 9 }
	
	 stateinputFailure2 OBJECT-TYPE
      	SYNTAX TruthValue
      	MAX-ACCESS read-only
      	STATUS current
      	DESCRIPTION
        	"Failure Active/Inactive:
        		active (1)   --> failure
        		inactive (2) --> no failure"
	::= { stateNotificationstx2 1 }
	
	statereferenceFailure2 OBJECT-TYPE
      	SYNTAX TruthValue
      	MAX-ACCESS read-only
      	STATUS current
      	DESCRIPTION
        	"Failure Active/Inactive:
        		active (1)   --> failure
        		inactive (2) --> no failure"
	::= { stateNotificationstx2 2 }
	
	stateppsFailure2 OBJECT-TYPE
      	SYNTAX TruthValue
      	MAX-ACCESS read-only
      	STATUS current
      	DESCRIPTION
        	"Failure Active/Inactive:
        		active (1)   --> failure
        		inactive (2) --> no failure"
	::= { stateNotificationstx2 3 }
	
	statewarningFailure2 OBJECT-TYPE
      	SYNTAX TruthValue
      	MAX-ACCESS read-only
      	STATUS current
      	DESCRIPTION
        	"Failure Active/Inactive:
        		active (1)   --> failure
        		inactive (2) --> no failure"
	::= { stateNotificationstx2 4 }
	
	statesumfaultFailure2 OBJECT-TYPE
      	SYNTAX TruthValue
      	MAX-ACCESS read-only
      	STATUS current
      	DESCRIPTION
        	"Failure Active/Inactive:
        		active (1)   --> failure
        		inactive (2) --> no failure"
	::= { stateNotificationstx2 5 }
	
	statenoResponseFailure2 OBJECT-TYPE
      	SYNTAX TruthValue
      	MAX-ACCESS read-only
      	STATUS current
      	DESCRIPTION
        	"Failure Active/Inactive:
        		active (1)   --> failure
        		inactive (2) --> no failure"
	::= { stateNotificationstx2 6 }
	
	stateantennaLoadFailure2 OBJECT-TYPE
      	SYNTAX TruthValue
      	MAX-ACCESS read-only
      	STATUS current
      	DESCRIPTION
        	"Failure Active/Inactive:
        		active (1)   --> Load
        		inactive (2) --> Antena"
	::= { stateNotificationstx2 7 }
	
	statepoutFailure2 OBJECT-TYPE
      	SYNTAX TruthValue
      	MAX-ACCESS read-only
      	STATUS current
      	DESCRIPTION
        	"Failure Active/Inactive:
        		active (1)   --> failure
        		inactive (2) --> no failure"
	::= { stateNotificationstx2 8 }
	
	statecoaxialswitchFailure2 OBJECT-TYPE
      	SYNTAX TruthValue
      	MAX-ACCESS read-only
      	STATUS current
      	DESCRIPTION
        	"Failure Active/Inactive:
        		active (1)   --> failure
        		inactive (2) --> no failure"
	::= { stateNotificationstx2 9 }
	
	 stateinputFailure3 OBJECT-TYPE
      	SYNTAX TruthValue
      	MAX-ACCESS read-only
      	STATUS current
      	DESCRIPTION
        	"Failure Active/Inactive:
        		active (1)   --> failure
        		inactive (2) --> no failure"
	::= { stateNotificationstx3 1 }
	
	statereferenceFailure3 OBJECT-TYPE
      	SYNTAX TruthValue
      	MAX-ACCESS read-only
      	STATUS current
      	DESCRIPTION
        	"Failure Active/Inactive:
        		active (1)   --> failure
        		inactive (2) --> no failure"
	::= { stateNotificationstx3 2 }
	
	stateppsFailure3 OBJECT-TYPE
      	SYNTAX TruthValue
      	MAX-ACCESS read-only
      	STATUS current
      	DESCRIPTION
        	"Failure Active/Inactive:
        		active (1)   --> failure
        		inactive (2) --> no failure"
	::= { stateNotificationstx3 3 }
	
	statewarningFailure3 OBJECT-TYPE
      	SYNTAX TruthValue
      	MAX-ACCESS read-only
      	STATUS current
      	DESCRIPTION
        	"Failure Active/Inactive:
        		active (1)   --> failure
        		inactive (2) --> no failure"
	::= { stateNotificationstx3 4 }
	
	statesumfaultFailure3 OBJECT-TYPE
      	SYNTAX TruthValue
      	MAX-ACCESS read-only
      	STATUS current
      	DESCRIPTION
        	"Failure Active/Inactive:
        		active (1)   --> failure
        		inactive (2) --> no failure"
	::= { stateNotificationstx3 5 }
	
	statenoResponseFailure3 OBJECT-TYPE
      	SYNTAX TruthValue
      	MAX-ACCESS read-only
      	STATUS current
      	DESCRIPTION
        	"Failure Active/Inactive:
        		active (1)   --> failure
        		inactive (2) --> no failure"
	::= { stateNotificationstx3 6 }
	
	stateantennaLoadFailure3 OBJECT-TYPE
      	SYNTAX TruthValue
      	MAX-ACCESS read-only
      	STATUS current
      	DESCRIPTION
        	"Failure Active/Inactive:
        		active (1)   --> Load
        		inactive (2) --> Antena"
	::= { stateNotificationstx3 7 }
	
	statepoutFailure3 OBJECT-TYPE
      	SYNTAX TruthValue
      	MAX-ACCESS read-only
      	STATUS current
      	DESCRIPTION
        	"Failure Active/Inactive:
        		active (1)   --> failure
        		inactive (2) --> no failure"
	::= { stateNotificationstx3 8 }
	
	statecoaxialswitchFailure3 OBJECT-TYPE
      	SYNTAX TruthValue
      	MAX-ACCESS read-only
      	STATUS current
      	DESCRIPTION
        	"Failure Active/Inactive:
        		active (1)   --> failure
        		inactive (2) --> no failure"
	::= { stateNotificationstx3 9 }
	
	 stateinputFailure4 OBJECT-TYPE
      	SYNTAX TruthValue
      	MAX-ACCESS read-only
      	STATUS current
      	DESCRIPTION
        	"Failure Active/Inactive:
        		active (1)   --> failure
        		inactive (2) --> no failure"
	::= { stateNotificationstx4 1 }
	
	statereferenceFailure4 OBJECT-TYPE
      	SYNTAX TruthValue
      	MAX-ACCESS read-only
      	STATUS current
      	DESCRIPTION
        	"Failure Active/Inactive:
        		active (1)   --> failure
        		inactive (2) --> no failure"
	::= { stateNotificationstx4 2 }
	
	stateppsFailure4 OBJECT-TYPE
      	SYNTAX TruthValue
      	MAX-ACCESS read-only
      	STATUS current
      	DESCRIPTION
        	"Failure Active/Inactive:
        		active (1)   --> failure
        		inactive (2) --> no failure"
	::= { stateNotificationstx4 3 }
	
	statewarningFailure4 OBJECT-TYPE
      	SYNTAX TruthValue
      	MAX-ACCESS read-only
      	STATUS current
      	DESCRIPTION
        	"Failure Active/Inactive:
        		active (1)   --> failure
        		inactive (2) --> no failure"
	::= { stateNotificationstx4 4 }
	
	statesumfaultFailure4 OBJECT-TYPE
      	SYNTAX TruthValue
      	MAX-ACCESS read-only
      	STATUS current
      	DESCRIPTION
        	"Failure Active/Inactive:
        		active (1)   --> failure
        		inactive (2) --> no failure"
	::= { stateNotificationstx4 5 }
	
	statenoResponseFailure4 OBJECT-TYPE
      	SYNTAX TruthValue
      	MAX-ACCESS read-only
      	STATUS current
      	DESCRIPTION
        	"Failure Active/Inactive:
        		active (1)   --> failure
        		inactive (2) --> no failure"
	::= { stateNotificationstx4 6 }
	
	stateantennaLoadFailure4 OBJECT-TYPE
      	SYNTAX TruthValue
      	MAX-ACCESS read-only
      	STATUS current
      	DESCRIPTION
        	"Failure Active/Inactive:
        		active (1)   --> Load
        		inactive (2) --> Antena"
	::= { stateNotificationstx4 7 }
	
	statepoutFailure4 OBJECT-TYPE
      	SYNTAX TruthValue
      	MAX-ACCESS read-only
      	STATUS current
      	DESCRIPTION
        	"Failure Active/Inactive:
        		active (1)   --> failure
        		inactive (2) --> no failure"
	::= { stateNotificationstx4 8 }
	
	statecoaxialswitchFailure4 OBJECT-TYPE
      	SYNTAX TruthValue
      	MAX-ACCESS read-only
      	STATUS current
      	DESCRIPTION
        	"Failure Active/Inactive:
        		active (1)   --> failure
        		inactive (2) --> no failure"
	::= { stateNotificationstx4 9 }
	
	 stateinputFailure5 OBJECT-TYPE
      	SYNTAX TruthValue
      	MAX-ACCESS read-only
      	STATUS current
      	DESCRIPTION
        	"Failure Active/Inactive:
        		active (1)   --> failure
        		inactive (2) --> no failure"
	::= { stateNotificationstx5 1 }
	
	statereferenceFailure5 OBJECT-TYPE
      	SYNTAX TruthValue
      	MAX-ACCESS read-only
      	STATUS current
      	DESCRIPTION
        	"Failure Active/Inactive:
        		active (1)   --> failure
        		inactive (2) --> no failure"
	::= { stateNotificationstx5 2 }
	
	stateppsFailure5 OBJECT-TYPE
      	SYNTAX TruthValue
      	MAX-ACCESS read-only
      	STATUS current
      	DESCRIPTION
        	"Failure Active/Inactive:
        		active (1)   --> failure
        		inactive (2) --> no failure"
	::= { stateNotificationstx5 3 }
	
	statewarningFailure5 OBJECT-TYPE
      	SYNTAX TruthValue
      	MAX-ACCESS read-only
      	STATUS current
      	DESCRIPTION
        	"Failure Active/Inactive:
        		active (1)   --> failure
        		inactive (2) --> no failure"
	::= { stateNotificationstx5 4 }
	
	statesumfaultFailure5 OBJECT-TYPE
      	SYNTAX TruthValue
      	MAX-ACCESS read-only
      	STATUS current
      	DESCRIPTION
        	"Failure Active/Inactive:
        		active (1)   --> failure
        		inactive (2) --> no failure"
	::= { stateNotificationstx5 5 }
	
	statenoResponseFailure5 OBJECT-TYPE
      	SYNTAX TruthValue
      	MAX-ACCESS read-only
      	STATUS current
      	DESCRIPTION
        	"Failure Active/Inactive:
        		active (1)   --> failure
        		inactive (2) --> no failure"
	::= { stateNotificationstx5 6 }
	
	stateantennaLoadFailure5 OBJECT-TYPE
      	SYNTAX TruthValue
      	MAX-ACCESS read-only
      	STATUS current
      	DESCRIPTION
        	"Failure Active/Inactive:
        		active (1)   --> Load
        		inactive (2) --> Antena"
	::= { stateNotificationstx5 7 }
	
	statepoutFailure5 OBJECT-TYPE
      	SYNTAX TruthValue
      	MAX-ACCESS read-only
      	STATUS current
      	DESCRIPTION
        	"Failure Active/Inactive:
        		active (1)   --> failure
        		inactive (2) --> no failure"
	::= { stateNotificationstx5 8 }
	
	statecoaxialswitchFailure5 OBJECT-TYPE
      	SYNTAX TruthValue
      	MAX-ACCESS read-only
      	STATUS current
      	DESCRIPTION
        	"Failure Active/Inactive:
        		active (1)   --> failure
        		inactive (2) --> no failure"
	::= { stateNotificationstx5 9 }
		
	 stateinputFailure6 OBJECT-TYPE
      	SYNTAX TruthValue
      	MAX-ACCESS read-only
      	STATUS current
      	DESCRIPTION
        	"Failure Active/Inactive:
        		active (1)   --> failure
        		inactive (2) --> no failure"
	::= { stateNotificationstx6 1 }
	
	statereferenceFailure6 OBJECT-TYPE
      	SYNTAX TruthValue
      	MAX-ACCESS read-only
      	STATUS current
      	DESCRIPTION
        	"Failure Active/Inactive:
        		active (1)   --> failure
        		inactive (2) --> no failure"
	::= { stateNotificationstx6 2 }
	
	stateppsFailure6 OBJECT-TYPE
      	SYNTAX TruthValue
      	MAX-ACCESS read-only
      	STATUS current
      	DESCRIPTION
        	"Failure Active/Inactive:
        		active (1)   --> failure
        		inactive (2) --> no failure"
	::= { stateNotificationstx6 3 }
	
	statewarningFailure6 OBJECT-TYPE
      	SYNTAX TruthValue
      	MAX-ACCESS read-only
      	STATUS current
      	DESCRIPTION
        	"Failure Active/Inactive:
        		active (1)   --> failure
        		inactive (2) --> no failure"
	::= { stateNotificationstx6 4 }
	
	statesumfaultFailure6 OBJECT-TYPE
      	SYNTAX TruthValue
      	MAX-ACCESS read-only
      	STATUS current
      	DESCRIPTION
        	"Failure Active/Inactive:
        		active (1)   --> failure
        		inactive (2) --> no failure"
	::= { stateNotificationstx6 5 }
	
	statenoResponseFailure6 OBJECT-TYPE
      	SYNTAX TruthValue
      	MAX-ACCESS read-only
      	STATUS current
      	DESCRIPTION
        	"Failure Active/Inactive:
        		active (1)   --> failure
        		inactive (2) --> no failure"
	::= { stateNotificationstx6 6 }
	
	stateantennaLoadFailure6 OBJECT-TYPE
      	SYNTAX TruthValue
      	MAX-ACCESS read-only
      	STATUS current
      	DESCRIPTION
        	"Failure Active/Inactive:
        		active (1)   --> Load
        		inactive (2) --> Antena"
	::= { stateNotificationstx6 7 }
	
	statepoutFailure6 OBJECT-TYPE
      	SYNTAX TruthValue
      	MAX-ACCESS read-only
      	STATUS current
      	DESCRIPTION
        	"Failure Active/Inactive:
        		active (1)   --> failure
        		inactive (2) --> no failure"
	::= { stateNotificationstx6 8 }
	
	statecoaxialswitchFailure6 OBJECT-TYPE
      	SYNTAX TruthValue
      	MAX-ACCESS read-only
      	STATUS current
      	DESCRIPTION
        	"Failure Active/Inactive:
        		active (1)   --> failure
        		inactive (2) --> no failure"
	::= { stateNotificationstx6 9 }
	
	 stateinputFailure7 OBJECT-TYPE
      	SYNTAX TruthValue
      	MAX-ACCESS read-only
      	STATUS current
      	DESCRIPTION
        	"Failure Active/Inactive:
        		active (1)   --> failure
        		inactive (2) --> no failure"
	::= { stateNotificationstx7 1 }
	
	statereferenceFailure7 OBJECT-TYPE
      	SYNTAX TruthValue
      	MAX-ACCESS read-only
      	STATUS current
      	DESCRIPTION
        	"Failure Active/Inactive:
        		active (1)   --> failure
        		inactive (2) --> no failure"
	::= { stateNotificationstx7 2 }
	
	stateppsFailure7 OBJECT-TYPE
      	SYNTAX TruthValue
      	MAX-ACCESS read-only
      	STATUS current
      	DESCRIPTION
        	"Failure Active/Inactive:
        		active (1)   --> failure
        		inactive (2) --> no failure"
	::= { stateNotificationstx7 3 }
	
	statewarningFailure7 OBJECT-TYPE
      	SYNTAX TruthValue
      	MAX-ACCESS read-only
      	STATUS current
      	DESCRIPTION
        	"Failure Active/Inactive:
        		active (1)   --> failure
        		inactive (2) --> no failure"
	::= { stateNotificationstx7 4 }
	
	statesumfaultFailure7 OBJECT-TYPE
      	SYNTAX TruthValue
      	MAX-ACCESS read-only
      	STATUS current
      	DESCRIPTION
        	"Failure Active/Inactive:
        		active (1)   --> failure
        		inactive (2) --> no failure"
	::= { stateNotificationstx7 5 }
	
	statenoResponseFailure7 OBJECT-TYPE
      	SYNTAX TruthValue
      	MAX-ACCESS read-only
      	STATUS current
      	DESCRIPTION
        	"Failure Active/Inactive:
        		active (1)   --> failure
        		inactive (2) --> no failure"
	::= { stateNotificationstx7 6 }
	
	stateantennaLoadFailure7 OBJECT-TYPE
      	SYNTAX TruthValue
      	MAX-ACCESS read-only
      	STATUS current
      	DESCRIPTION
        	"Failure Active/Inactive:
        		active (1)   --> Load
        		inactive (2) --> Antena"
	::= { stateNotificationstx7 7 }
	
	statepoutFailure7 OBJECT-TYPE
      	SYNTAX TruthValue
      	MAX-ACCESS read-only
      	STATUS current
      	DESCRIPTION
        	"Failure Active/Inactive:
        		active (1)   --> failure
        		inactive (2) --> no failure"
	::= { stateNotificationstx7 8 }
	
	statecoaxialswitchFailure7 OBJECT-TYPE
      	SYNTAX TruthValue
      	MAX-ACCESS read-only
      	STATUS current
      	DESCRIPTION
        	"Failure Active/Inactive:
        		active (1)   --> failure
        		inactive (2) --> no failure"
	::= { stateNotificationstx7 9 }
	
	 stateinputFailure8 OBJECT-TYPE
      	SYNTAX TruthValue
      	MAX-ACCESS read-only
      	STATUS current
      	DESCRIPTION
        	"Failure Active/Inactive:
        		active (1)   --> failure
        		inactive (2) --> no failure"
	::= { stateNotificationstx8 1 }
	
	statereferenceFailure8 OBJECT-TYPE
      	SYNTAX TruthValue
      	MAX-ACCESS read-only
      	STATUS current
      	DESCRIPTION
        	"Failure Active/Inactive:
        		active (1)   --> failure
        		inactive (2) --> no failure"
	::= { stateNotificationstx8 2 }
	
	stateppsFailure8 OBJECT-TYPE
      	SYNTAX TruthValue
      	MAX-ACCESS read-only
      	STATUS current
      	DESCRIPTION
        	"Failure Active/Inactive:
        		active (1)   --> failure
        		inactive (2) --> no failure"
	::= { stateNotificationstx8 3 }
	
	statewarningFailure8 OBJECT-TYPE
      	SYNTAX TruthValue
      	MAX-ACCESS read-only
      	STATUS current
      	DESCRIPTION
        	"Failure Active/Inactive:
        		active (1)   --> failure
        		inactive (2) --> no failure"
	::= { stateNotificationstx8 4 }
	
	statesumfaultFailure8 OBJECT-TYPE
      	SYNTAX TruthValue
      	MAX-ACCESS read-only
      	STATUS current
      	DESCRIPTION
        	"Failure Active/Inactive:
        		active (1)   --> failure
        		inactive (2) --> no failure"
	::= { stateNotificationstx8 5 }
	
	statenoResponseFailure8 OBJECT-TYPE
      	SYNTAX TruthValue
      	MAX-ACCESS read-only
      	STATUS current
      	DESCRIPTION
        	"Failure Active/Inactive:
        		active (1)   --> failure
        		inactive (2) --> no failure"
	::= { stateNotificationstx8 6 }
	
	stateantennaLoadFailure8 OBJECT-TYPE
      	SYNTAX TruthValue
      	MAX-ACCESS read-only
      	STATUS current
      	DESCRIPTION
        	"Failure Active/Inactive:
        		active (1)   --> Load
        		inactive (2) --> Antena"
	::= { stateNotificationstx8 7 }
	
	statepoutFailure8 OBJECT-TYPE
      	SYNTAX TruthValue
      	MAX-ACCESS read-only
      	STATUS current
      	DESCRIPTION
        	"Failure Active/Inactive:
        		active (1)   --> failure
        		inactive (2) --> no failure"
	::= { stateNotificationstx8 8 }
	
	statecoaxialswitchFailure8 OBJECT-TYPE
      	SYNTAX TruthValue
      	MAX-ACCESS read-only
      	STATUS current
      	DESCRIPTION
        	"Failure Active/Inactive:
        		active (1)   --> failure
        		inactive (2) --> no failure"
	::= { stateNotificationstx8 9 }
	
	 stateinputFailureR OBJECT-TYPE
      	SYNTAX TruthValue
      	MAX-ACCESS read-only
      	STATUS current
      	DESCRIPTION
        	"Failure Active/Inactive:
        		active (1)   --> failure
        		inactive (2) --> no failure"
	::= { stateNotificationstxR 1 }
	
	statereferenceFailureR OBJECT-TYPE
      	SYNTAX TruthValue
      	MAX-ACCESS read-only
      	STATUS current
      	DESCRIPTION
        	"Failure Active/Inactive:
        		active (1)   --> failure
        		inactive (2) --> no failure"
	::= { stateNotificationstxR 2 }
	
	stateppsFailureR OBJECT-TYPE
      	SYNTAX TruthValue
      	MAX-ACCESS read-only
      	STATUS current
      	DESCRIPTION
        	"Failure Active/Inactive:
        		active (1)   --> failure
        		inactive (2) --> no failure"
	::= { stateNotificationstxR 3 }
	
	statewarningFailureR OBJECT-TYPE
      	SYNTAX TruthValue
      	MAX-ACCESS read-only
      	STATUS current
      	DESCRIPTION
        	"Failure Active/Inactive:
        		active (1)   --> failure
        		inactive (2) --> no failure"
	::= { stateNotificationstxR 4 }
	
	statesumfaultFailureR OBJECT-TYPE
      	SYNTAX TruthValue
      	MAX-ACCESS read-only
      	STATUS current
      	DESCRIPTION
        	"Failure Active/Inactive:
        		active (1)   --> failure
        		inactive (2) --> no failure"
	::= { stateNotificationstxR 5 }
	
	statenoResponseFailureR OBJECT-TYPE
      	SYNTAX TruthValue
      	MAX-ACCESS read-only
      	STATUS current
      	DESCRIPTION
        	"Failure Active/Inactive:
        		active (1)   --> failure
        		inactive (2) --> no failure"
	::= { stateNotificationstxR 6 }
	
	stateantennaLoadFailureR OBJECT-TYPE
      	SYNTAX TruthValue
      	MAX-ACCESS read-only
      	STATUS current
      	DESCRIPTION
        	"Failure Active/Inactive:
        		active (1)   --> Load
        		inactive (2) --> Antena"
	::= { stateNotificationstxR 7 }
	
	statepoutFailureR OBJECT-TYPE
      	SYNTAX TruthValue
      	MAX-ACCESS read-only
      	STATUS current
      	DESCRIPTION
        	"Failure Active/Inactive:
        		active (1)   --> failure
        		inactive (2) --> no failure"
	::= { stateNotificationstxR 8 }

--------------------------------------------------------------------------	

	statenoResponseMatrix OBJECT-TYPE
      	SYNTAX TruthValue
      	MAX-ACCESS read-only
      	STATUS current
      	DESCRIPTION
        	"Failure Active/Inactive:
        		active (1)   --> failure
        		inactive (2) --> no failure"
	::= { stateNotificationsMatrix 1 }

--------------------------------------------------------------------------	

	statepoutFailure OBJECT-TYPE
      	SYNTAX TruthValue
      	MAX-ACCESS read-only
      	STATUS current
      	DESCRIPTION
        	"Failure Active/Inactive:
        		active (1)   --> failure
        		inactive (2) --> no failure"
	::= { stateNotificationspower 1 }
	
	statereflectedFailure OBJECT-TYPE
      	SYNTAX TruthValue
      	MAX-ACCESS read-only
      	STATUS current
      	DESCRIPTION
        	"Failure Active/Inactive:
        		active (1)   --> failure
        		inactive (2) --> no failure"
	::= { stateNotificationspower 2 }
	
--------------------------------------------------------------------------	
	
	statetemperatureFailure OBJECT-TYPE
      	SYNTAX TruthValue
      	MAX-ACCESS read-only
      	STATUS current
      	DESCRIPTION
        	"Failure Active/Inactive:
        		active (1)   --> failure
        		inactive (2) --> no failure"
	::= { stateNotificationsrack 1 }
	
	stateturbine1Failure OBJECT-TYPE
      	SYNTAX TruthValue
      	MAX-ACCESS read-only
      	STATUS current
      	DESCRIPTION
        	"Failure Active/Inactive:
        		active (1)   --> failure
        		inactive (2) --> no failure"
	::= { stateNotificationsrack 2 }
	
	stateturbine2Failure OBJECT-TYPE
      	SYNTAX TruthValue
      	MAX-ACCESS read-only
      	STATUS current
      	DESCRIPTION
        	"Failure Active/Inactive:
        		active (1)   --> failure
        		inactive (2) --> no failure"
	::= { stateNotificationsrack 3 }
	
	statecoaxialswitchFailure OBJECT-TYPE
      	SYNTAX TruthValue
      	MAX-ACCESS read-only
      	STATUS current
      	DESCRIPTION
        	"Failure Active/Inactive:
        		active (1)   --> failure
        		inactive (2) --> no failure"
	::= { stateNotificationsrack 4 }
	
	stateamplifierFailure OBJECT-TYPE
      	SYNTAX TruthValue
      	MAX-ACCESS read-only
      	STATUS current
      	DESCRIPTION
        	"Failure Active/Inactive:
        		active (1)   --> failure
        		inactive (2) --> no failure"
	::= { stateNotificationsrack 5 }
	
	statepowersupplyFailure OBJECT-TYPE
      	SYNTAX TruthValue
      	MAX-ACCESS read-only
      	STATUS current
      	DESCRIPTION
        	"Failure Active/Inactive:
        		active (1)   --> failure
        		inactive (2) --> no failure"
	::= { stateNotificationsrack 6 }
	
	
	stateflow1Faultrack1 OBJECT-TYPE
      	SYNTAX TruthValue
      	MAX-ACCESS read-only
      	STATUS current
      	DESCRIPTION
        	"Failure Active/Inactive:
        		active (1)   --> failure
        		inactive (2) --> no failure"
	::= { stateNotificationsrack 7 }
	
	stateflow2Faultrack1 OBJECT-TYPE
      	SYNTAX TruthValue
      	MAX-ACCESS read-only
      	STATUS current
      	DESCRIPTION
        	"Failure Active/Inactive:
        		active (1)   --> failure
        		inactive (2) --> no failure"
	::= { stateNotificationsrack 8 }
	
	statePumpsLinkrack1 OBJECT-TYPE
      	SYNTAX TruthValue
      	MAX-ACCESS read-only
      	STATUS current
      	DESCRIPTION
        	"Failure Active/Inactive:
        		active (1)   --> failure
        		inactive (2) --> no failure"
	::= { stateNotificationsrack 9 }
	
	stateSecLooprack1 OBJECT-TYPE
      	SYNTAX TruthValue
      	MAX-ACCESS read-only
      	STATUS current
      	DESCRIPTION
        	"Failure Active/Inactive:
        		active (1)   --> failure
        		inactive (2) --> no failure"
	::= { stateNotificationsrack 10 }
	
	stateMainLooprack1 OBJECT-TYPE
      	SYNTAX TruthValue
      	MAX-ACCESS read-only
      	STATUS current
      	DESCRIPTION
        	"Failure Active/Inactive:
        		active (1)   --> failure
        		inactive (2) --> no failure"
	::= { stateNotificationsrack 11 }
	
	stateAuxPowerrack1 OBJECT-TYPE
      	SYNTAX TruthValue
      	MAX-ACCESS read-only
      	STATUS current
      	DESCRIPTION
        	"Failure Active/Inactive:
        		active (1)   --> failure
        		inactive (2) --> no failure"
	::= { stateNotificationsrack 12 }
	
	stateCoolingrack1 OBJECT-TYPE
      	SYNTAX TruthValue
      	MAX-ACCESS read-only
      	STATUS current
      	DESCRIPTION
        	"Failure Active/Inactive:
        		active (1)   --> failure
        		inactive (2) --> no failure"
	::= { stateNotificationsrack 13 }
	
	statePressureFaultrack1 OBJECT-TYPE
      	SYNTAX TruthValue
      	MAX-ACCESS read-only
      	STATUS current
      	DESCRIPTION
        	"Failure Active/Inactive:
        		active (1)   --> failure
        		inactive (2) --> no failure"
	::= { stateNotificationsrack 14 }
	
	stateCoolingPowerrack1 OBJECT-TYPE
      	SYNTAX TruthValue
      	MAX-ACCESS read-only
      	STATUS current
      	DESCRIPTION
        	"Failure Active/Inactive:
        		active (1)   --> failure
        		inactive (2) --> no failure"
	::= { stateNotificationsrack 15 }
	
	stateExchangeFan1Comrack1 OBJECT-TYPE
      	SYNTAX TruthValue
      	MAX-ACCESS read-only
      	STATUS current
      	DESCRIPTION
        	"Failure Active/Inactive:
        		active (1)   --> failure
        		inactive (2) --> no failure"
	::= { stateNotificationsrack 16 }
	
	stateExchangeFan2Comrack1 OBJECT-TYPE
      	SYNTAX TruthValue
      	MAX-ACCESS read-only
      	STATUS current
      	DESCRIPTION
        	"Failure Active/Inactive:
        		active (1)   --> failure
        		inactive (2) --> no failure"
	::= { stateNotificationsrack 17 }
		
	statePump1Faultrack1 OBJECT-TYPE
      	SYNTAX TruthValue
      	MAX-ACCESS read-only
      	STATUS current
      	DESCRIPTION
        	"Failure Active/Inactive:
        		active (1)   --> failure
        		inactive (2) --> no failure"
	::= { stateNotificationsrack 18 }
	
	statePump2Faultrack1 OBJECT-TYPE
      	SYNTAX TruthValue
      	MAX-ACCESS read-only
      	STATUS current
      	DESCRIPTION
        	"Failure Active/Inactive:
        		active (1)   --> failure
        		inactive (2) --> no failure"
	::= { stateNotificationsrack 19 }
	
	stateExchangeFan1Faultrack1 OBJECT-TYPE
      	SYNTAX TruthValue
      	MAX-ACCESS read-only
      	STATUS current
      	DESCRIPTION
        	"Failure Active/Inactive:
        		active (1)   --> failure
        		inactive (2) --> no failure"
	::= { stateNotificationsrack 20 }
	
	stateExchangeFan2Faultrack1 OBJECT-TYPE
      	SYNTAX TruthValue
      	MAX-ACCESS read-only
      	STATUS current
      	DESCRIPTION
        	"Failure Active/Inactive:
        		active (1)   --> failure
        		inactive (2) --> no failure"
	::= { stateNotificationsrack 21 }
	
	stateExchangeLinkrack1 OBJECT-TYPE
      	SYNTAX TruthValue
      	MAX-ACCESS read-only
      	STATUS current
      	DESCRIPTION
        	"Failure Active/Inactive:
        		active (1)   --> failure
        		inactive (2) --> no failure"
	::= { stateNotificationsrack 22 }
	
	stateExchangePowerrack1 OBJECT-TYPE
      	SYNTAX TruthValue
      	MAX-ACCESS read-only
      	STATUS current
      	DESCRIPTION
        	"Failure Active/Inactive:
        		active (1)   --> failure
        		inactive (2) --> no failure"
	::= { stateNotificationsrack 23 }
	
	statePump1Linkrack1 OBJECT-TYPE
      	SYNTAX TruthValue
      	MAX-ACCESS read-only
      	STATUS current
      	DESCRIPTION
        	"Failure Active/Inactive:
        		active (1)   --> failure
        		inactive (2) --> no failure"
	::= { stateNotificationsrack 24 }
	
	statePump2Linkrack1 OBJECT-TYPE
      	SYNTAX TruthValue
      	MAX-ACCESS read-only
      	STATUS current
      	DESCRIPTION
        	"Failure Active/Inactive:
        		active (1)   --> failure
        		inactive (2) --> no failure"
	::= { stateNotificationsrack 25 }

	stateflow1Faultrack2 OBJECT-TYPE
      	SYNTAX TruthValue
      	MAX-ACCESS read-only
      	STATUS current
      	DESCRIPTION
        	"Failure Active/Inactive:
        		active (1)   --> failure
        		inactive (2) --> no failure"
	::= { stateNotificationsrack 26 }
	
	stateflow2Faultrack2 OBJECT-TYPE
      	SYNTAX TruthValue
      	MAX-ACCESS read-only
      	STATUS current
      	DESCRIPTION
        	"Failure Active/Inactive:
        		active (1)   --> failure
        		inactive (2) --> no failure"
	::= { stateNotificationsrack 27 }
	
	statePumpsLinkrack2 OBJECT-TYPE
      	SYNTAX TruthValue
      	MAX-ACCESS read-only
      	STATUS current
      	DESCRIPTION
        	"Failure Active/Inactive:
        		active (1)   --> failure
        		inactive (2) --> no failure"
	::= { stateNotificationsrack 28 }
	
	stateSecLooprack2 OBJECT-TYPE
      	SYNTAX TruthValue
      	MAX-ACCESS read-only
      	STATUS current
      	DESCRIPTION
        	"Failure Active/Inactive:
        		active (1)   --> failure
        		inactive (2) --> no failure"
	::= { stateNotificationsrack 29 }
	
	stateMainLooprack2 OBJECT-TYPE
      	SYNTAX TruthValue
      	MAX-ACCESS read-only
      	STATUS current
      	DESCRIPTION
        	"Failure Active/Inactive:
        		active (1)   --> failure
        		inactive (2) --> no failure"
	::= { stateNotificationsrack 30 }
	
	stateAuxPowerrack2 OBJECT-TYPE
      	SYNTAX TruthValue
      	MAX-ACCESS read-only
      	STATUS current
      	DESCRIPTION
        	"Failure Active/Inactive:
        		active (1)   --> failure
        		inactive (2) --> no failure"
	::= { stateNotificationsrack 31 }
	
	stateCoolingrack2 OBJECT-TYPE
      	SYNTAX TruthValue
      	MAX-ACCESS read-only
      	STATUS current
      	DESCRIPTION
        	"Failure Active/Inactive:
        		active (1)   --> failure
        		inactive (2) --> no failure"
	::= { stateNotificationsrack 32 }
	
	statePressureFaultrack2 OBJECT-TYPE
      	SYNTAX TruthValue
      	MAX-ACCESS read-only
      	STATUS current
      	DESCRIPTION
        	"Failure Active/Inactive:
        		active (1)   --> failure
        		inactive (2) --> no failure"
	::= { stateNotificationsrack 33 }
	
	stateCoolingPowerrack2 OBJECT-TYPE
      	SYNTAX TruthValue
      	MAX-ACCESS read-only
      	STATUS current
      	DESCRIPTION
        	"Failure Active/Inactive:
        		active (1)   --> failure
        		inactive (2) --> no failure"
	::= { stateNotificationsrack 34 }
	
	stateExchangeFan1Comrack2 OBJECT-TYPE
      	SYNTAX TruthValue
      	MAX-ACCESS read-only
      	STATUS current
      	DESCRIPTION
        	"Failure Active/Inactive:
        		active (1)   --> failure
        		inactive (2) --> no failure"
	::= { stateNotificationsrack 35 }
	
	stateExchangeFan2Comrack2 OBJECT-TYPE
      	SYNTAX TruthValue
      	MAX-ACCESS read-only
      	STATUS current
      	DESCRIPTION
        	"Failure Active/Inactive:
        		active (1)   --> failure
        		inactive (2) --> no failure"
	::= { stateNotificationsrack 36 }
		
	statePump1Faultrack2 OBJECT-TYPE
      	SYNTAX TruthValue
      	MAX-ACCESS read-only
      	STATUS current
      	DESCRIPTION
        	"Failure Active/Inactive:
        		active (1)   --> failure
        		inactive (2) --> no failure"
	::= { stateNotificationsrack 37 }
	
	statePump2Faultrack2 OBJECT-TYPE
      	SYNTAX TruthValue
      	MAX-ACCESS read-only
      	STATUS current
      	DESCRIPTION
        	"Failure Active/Inactive:
        		active (1)   --> failure
        		inactive (2) --> no failure"
	::= { stateNotificationsrack 38 }
	
	stateExchangeFan1Faultrack2 OBJECT-TYPE
      	SYNTAX TruthValue
      	MAX-ACCESS read-only
      	STATUS current
      	DESCRIPTION
        	"Failure Active/Inactive:
        		active (1)   --> failure
        		inactive (2) --> no failure"
	::= { stateNotificationsrack 39 }
	
	stateExchangeFan2Faultrack2 OBJECT-TYPE
      	SYNTAX TruthValue
      	MAX-ACCESS read-only
      	STATUS current
      	DESCRIPTION
        	"Failure Active/Inactive:
        		active (1)   --> failure
        		inactive (2) --> no failure"
	::= { stateNotificationsrack 40 }
	
	stateExchangeLinkrack2 OBJECT-TYPE
      	SYNTAX TruthValue
      	MAX-ACCESS read-only
      	STATUS current
      	DESCRIPTION
        	"Failure Active/Inactive:
        		active (1)   --> failure
        		inactive (2) --> no failure"
	::= { stateNotificationsrack 41 }
	
	stateExchangePowerrack2 OBJECT-TYPE
      	SYNTAX TruthValue
      	MAX-ACCESS read-only
      	STATUS current
      	DESCRIPTION
        	"Failure Active/Inactive:
        		active (1)   --> failure
        		inactive (2) --> no failure"
	::= { stateNotificationsrack 42 }
	
	statePump1Linkrack2 OBJECT-TYPE
      	SYNTAX TruthValue
      	MAX-ACCESS read-only
      	STATUS current
      	DESCRIPTION
        	"Failure Active/Inactive:
        		active (1)   --> failure
        		inactive (2) --> no failure"
	::= { stateNotificationsrack 43 }
	
	statePump2Linkrack2 OBJECT-TYPE
      	SYNTAX TruthValue
      	MAX-ACCESS read-only
      	STATUS current
      	DESCRIPTION
        	"Failure Active/Inactive:
        		active (1)   --> failure
        		inactive (2) --> no failure"
	::= { stateNotificationsrack 44 }
------------------------------------------------------------------------

	stateinputexcAFailure OBJECT-TYPE
      	SYNTAX TruthValue
      	MAX-ACCESS read-only
      	STATUS current
      	DESCRIPTION
        	"Failure Active/Inactive:
        		active (1)   --> failure
        		inactive (2) --> no failure"
	::= { stateNotificationsexcA 1 }
	
	statereferenceexcAFailure OBJECT-TYPE
      	SYNTAX TruthValue
      	MAX-ACCESS read-only
      	STATUS current
      	DESCRIPTION
        	"Failure Active/Inactive:
        		active (1)   --> failure
        		inactive (2) --> no failure"
	::= { stateNotificationsexcA 2 }
	
	stateppsexcAFailure OBJECT-TYPE
      	SYNTAX TruthValue
      	MAX-ACCESS read-only
      	STATUS current
      	DESCRIPTION
        	"Failure Active/Inactive:
        		active (1)   --> failure
        		inactive (2) --> no failure"
	::= { stateNotificationsexcA 3 }
	
	statewarningexcAFailure OBJECT-TYPE
      	SYNTAX TruthValue
      	MAX-ACCESS read-only
      	STATUS current
      	DESCRIPTION
        	"Failure Active/Inactive:
        		active (1)   --> failure
        		inactive (2) --> no failure"
	::= { stateNotificationsexcA 4 }
	
	statefaultexcAFailure OBJECT-TYPE
      	SYNTAX TruthValue
      	MAX-ACCESS read-only
      	STATUS current
      	DESCRIPTION
        	"Failure Active/Inactive:
        		active (1)   --> failure
        		inactive (2) --> no failure"
	::= { stateNotificationsexcA 5 }
	
	stateoutputPowerexcAFailure OBJECT-TYPE
      	SYNTAX TruthValue
      	MAX-ACCESS read-only
      	STATUS current
      	DESCRIPTION
        	"Failure Active/Inactive:
        		active (1)   --> failure
        		inactive (2) --> no failure"
	::= { stateNotificationsexcA 6 }
	
	statenoResponseexcAFailure OBJECT-TYPE
      	SYNTAX TruthValue
      	MAX-ACCESS read-only
      	STATUS current
      	DESCRIPTION
        	"Failure Active/Inactive:
        		active (1)   --> failure
        		inactive (2) --> no failure"
	::= { stateNotificationsexcA 7 }
	
	stateantennaLoadexcA OBJECT-TYPE
      	SYNTAX TruthValue
      	MAX-ACCESS read-only
      	STATUS current
      	DESCRIPTION
        	"Failure Active/Inactive:
        		active (1)   --> failure
        		inactive (2) --> no failure"
	::= { stateNotificationsexcA 8 }

------------------------------------------------------------------
	
	stateinputexcBFailure OBJECT-TYPE
      	SYNTAX TruthValue
      	MAX-ACCESS read-only
      	STATUS current
      	DESCRIPTION
        	"Failure Active/Inactive:
        		active (1)   --> failure
        		inactive (2) --> no failure"
	::= { stateNotificationsexcB 1 }
	
	statereferenceexcBFailure OBJECT-TYPE
      	SYNTAX TruthValue
      	MAX-ACCESS read-only
      	STATUS current
      	DESCRIPTION
        	"Failure Active/Inactive:
        		active (1)   --> failure
        		inactive (2) --> no failure"
	::= { stateNotificationsexcB 2 }
	
	stateppsexcBFailure OBJECT-TYPE
      	SYNTAX TruthValue
      	MAX-ACCESS read-only
      	STATUS current
      	DESCRIPTION
        	"Failure Active/Inactive:
        		active (1)   --> failure
        		inactive (2) --> no failure"
	::= { stateNotificationsexcB 3 }
	
	statewarningexcBFailure OBJECT-TYPE
      	SYNTAX TruthValue
      	MAX-ACCESS read-only
      	STATUS current
      	DESCRIPTION
        	"Failure Active/Inactive:
        		active (1)   --> failure
        		inactive (2) --> no failure"
	::= { stateNotificationsexcB 4 }
	
	statefaultexcBFailure OBJECT-TYPE
      	SYNTAX TruthValue
      	MAX-ACCESS read-only
      	STATUS current
      	DESCRIPTION
        	"Failure Active/Inactive:
        		active (1)   --> failure
        		inactive (2) --> no failure"
	::= { stateNotificationsexcB 5 }
	
	stateoutputPowerexcBFailure OBJECT-TYPE
      	SYNTAX TruthValue
      	MAX-ACCESS read-only
      	STATUS current
      	DESCRIPTION
        	"Failure Active/Inactive:
        		active (1)   --> failure
        		inactive (2) --> no failure"
	::= { stateNotificationsexcB 6 }
	
	statenoResponseexcBFailure OBJECT-TYPE
      	SYNTAX TruthValue
      	MAX-ACCESS read-only
      	STATUS current
      	DESCRIPTION
        	"Failure Active/Inactive:
        		active (1)   --> failure
        		inactive (2) --> no failure"
	::= { stateNotificationsexcB 7 }
	
	stateantennaLoadexcB OBJECT-TYPE
      	SYNTAX TruthValue
      	MAX-ACCESS read-only
      	STATUS current
      	DESCRIPTION
        	"Failure Active/Inactive:
        		active (1)   --> failure
        		inactive (2) --> no failure"
	::= { stateNotificationsexcB 8 }
	
------------------------------------------------------------------

	stateswitchSystemReady OBJECT-TYPE
      	SYNTAX TruthValue
      	MAX-ACCESS read-only
      	STATUS current
      	DESCRIPTION
        	"Failure Active/Inactive:
        		active (1)   --> failure
        		inactive (2) --> no failure"
	::= { stateNotificationsccu 1 }
	
	stateccuFault OBJECT-TYPE
      	SYNTAX TruthValue
      	MAX-ACCESS read-only
      	STATUS current
      	DESCRIPTION
        	"Failure Active/Inactive:
        		active (1)   --> failure
        		inactive (2) --> no failure"
	::= { stateNotificationsccu 2 }
	
	stateinterlockFailure OBJECT-TYPE
      	SYNTAX TruthValue
      	MAX-ACCESS read-only
      	STATUS current
      	DESCRIPTION
        	"Failure Active/Inactive:
        		active (1)   --> failure
        		inactive (2) --> no failure"
	::= { stateNotificationsccu 3 }
---------------------------------------------------------------------------
	stategpslockAFailure OBJECT-TYPE
      	SYNTAX TruthValue
      	MAX-ACCESS read-only
      	STATUS current
      	DESCRIPTION
        	"Failure Active/Inactive:
        		active (1)   --> failure
        		inactive (2) --> no failure"
	::= { stateNotificationsgps 1 }
	
	statesfnreadyAFailure OBJECT-TYPE
      	SYNTAX TruthValue
      	MAX-ACCESS read-only
      	STATUS current
      	DESCRIPTION
        	"Failure Active/Inactive:
        		active (1)   --> failure
        		inactive (2) --> no failure"
	::= { stateNotificationsgps 2 }
	
	statevccAFailure OBJECT-TYPE
      	SYNTAX TruthValue
      	MAX-ACCESS read-only
      	STATUS current
      	DESCRIPTION
        	"Failure Active/Inactive:
        		active (1)   --> failure
        		inactive (2) --> no failure"
	::= { stateNotificationsgps 3 }
	
	stategpslockBFailure OBJECT-TYPE
      	SYNTAX TruthValue
      	MAX-ACCESS read-only
      	STATUS current
      	DESCRIPTION
        	"Failure Active/Inactive:
        		active (1)   --> failure
        		inactive (2) --> no failure"
	::= { stateNotificationsgps 4 }
	
	statesfnreadyBFailure OBJECT-TYPE
      	SYNTAX TruthValue
      	MAX-ACCESS read-only
      	STATUS current
      	DESCRIPTION
        	"Failure Active/Inactive:
        		active (1)   --> failure
        		inactive (2) --> no failure"
	::= { stateNotificationsgps 5 }
	
	statevccBFailure OBJECT-TYPE
      	SYNTAX TruthValue
      	MAX-ACCESS read-only
      	STATUS current
      	DESCRIPTION
        	"Failure Active/Inactive:
        		active (1)   --> failure
        		inactive (2) --> no failure"
	::= { stateNotificationsgps 6 }
	
	statewarningGPS OBJECT-TYPE
      	SYNTAX TruthValue
      	MAX-ACCESS read-only
      	STATUS current
      	DESCRIPTION
        	"Failure Active/Inactive:
        		active (1)   --> failure
        		inactive (2) --> no failure"
	::= { stateNotificationsgps 7 }
	
	statefaultGPS OBJECT-TYPE
      	SYNTAX TruthValue
      	MAX-ACCESS read-only
      	STATUS current
      	DESCRIPTION
        	"Failure Active/Inactive:
        		active (1)   --> failure
        		inactive (2) --> no failure"
	::= { stateNotificationsgps 8 }
	
	statenoResponseGPS OBJECT-TYPE
      	SYNTAX TruthValue
      	MAX-ACCESS read-only
      	STATUS current
      	DESCRIPTION
        	"Failure Active/Inactive:
        		active (1)   --> failure
        		inactive (2) --> no failure"
	::= { stateNotificationsgps 9 }
	
	
---------------------------------------------------------------------------	
---------------------------------------------------------------------------
  	END
